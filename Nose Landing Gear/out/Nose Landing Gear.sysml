library package 'Nose Landing Gear Library' {
    private import ARCADIA::*; 
    @PackageMeta {
        type = "Library";
    } 
    @CapellaID { eid = "f9dad0df-a4cb-4073-a81e-f329162ac879"; } 
    enum def 'ProgressStatus' :> EnumerationPropertyType  { 
        enum 'DRAFT'; 
        enum 'TO_BE_REVIEWED'; 
        enum 'TO_BE_DISCUSSED'; 
        enum 'REWORK_NECESSARY'; 
        enum 'UNDER_REWORK'; 
        enum 'REVIEWED_OK'; 
    }  
    item '3f6c88bd-7340-449f-93f0-0cc2522e9aa0' : ModelInformation  { 
        @CapellaID { eid = "3f6c88bd-7340-449f-93f0-0cc2522e9aa0"; } 
    }  
    package 'Nose Landing Gear' {
        @PackageMeta {
            type = "SystemEngineering";
        } 
        @CapellaID { eid = "f5dbfa51-e49a-44d1-ac1b-d5062f1ee26c"; } 
        package 'PLM Data' {
            @PackageMeta {
                type = "GroupingElementPkg";
            } 
            @CapellaID { eid = "0e63ae62-b04e-4b84-bd33-0389ac180e04"; } 
            package 'PLM Requirement Types' {
                @PackageMeta {
                    type = "CapellaTypesFolder";
                } 
                @CapellaID { eid = "2e1c30a3-8aae-4b23-bb90-0e90508a0d46"; } 
                requirement def <'SMW_DEFAULT_PLM_REQ_MODULE'> 'PLM Requirement Module' :> ReqIFRequirement { 
                    @CapellaID { eid = "57912dcf-0f70-4d2b-9497-a374c65e9d96"; } 
                }  
                requirement def <'PlmRequirement'> 'PlmRequirement' :> ReqIFRequirement { 
                    @CapellaID { eid = "bdc1c0b7-0b5a-40c6-8aa3-e8c28dc860df"; } 
                }  
            } 
            requirement 'PLM Requirements' : 'PLM Requirement Types'::'PLM Requirement Module'  { 
                @CapellaID { eid = "c5c56ac3-5739-4d72-9894-b5208e6f6fa2"; } 
                requirement <'REQ-000841/A'> 'Retract Cycle Time' : 'PLM Requirement Types'::'PlmRequirement'  { 
                    doc /*
                    <p style="margin-top:0pt; margin-bottom:0pt; font-size:10pt"><span style="font-family:'Times New Roman'; font-size: 10pt; font-family: 'Times New Roman'">The Retract and Extend functional chain shall complete a full gear retraction cycle, from Manage NLG command to Apply Force Runway completion, within 8 seconds.</span></p><p style="margin-top:0pt; margin-bottom:0pt; font-size:10pt"><span style="font-family:'Times New Roman'; font-size: 10pt; font-family: 'Times New Roman'">Rationale: 8 seconds aligns with the aircraft-level landing gear retraction time allocated in the top-level operational requirements.</span></p>
                    */ 
                    @CapellaID { eid = "dbc2bc9e-af93-4d7a-bb00-56d7c9ab4c89"; } 
                    satisfy 'Nose Landing Gear Library'::'Nose Landing Gear'::'PLM Data'::'PLM Requirements'.'Retract Cycle Time'  by
                        'Physical Architecture'::'Physical Functions'::'Root Physical Function'.'Retract and Extend '; 
                     
                }  
                requirement <'REQ-000839/A'> 'Extension Cycle Time' : 'PLM Requirement Types'::'PlmRequirement'  { 
                    doc /*
                    <p style="margin-top:0pt; margin-bottom:0pt; font-size:10pt"><span style="font-family:'Times New Roman'; font-size: 10pt; font-family: 'Times New Roman'">The Retract and Extend functional chain shall complete a full gear extension cycle within 10 seconds of Manage NLG receiving the Extend signal.</span></p><p style="margin-top:0pt; margin-bottom:0pt; font-size:10pt"><span style="font-family:'Times New Roman'; font-size: 10pt; font-family: 'Times New Roman'">Rationale: 10 seconds accounts for the added time margin required for gravity-assisted free-fall extension in a backup scenario.</span></p>
                    */ 
                    @CapellaID { eid = "fb9f0564-384d-4b58-850d-591e74699256"; } 
                    satisfy 'Nose Landing Gear Library'::'Nose Landing Gear'::'PLM Data'::'PLM Requirements'.'Extension Cycle Time'  by
                        'Physical Architecture'::'Physical Functions'::'Root Physical Function'.'Retract and Extend '; 
                     
                }  
                requirement <'REQ-000835/A'> 'Force Transfer Integrity' : 'PLM Requirement Types'::'PlmRequirement'  { 
                    doc /*
                    <p style="margin-top:0pt; margin-bottom:0pt; font-size:10pt"><span style="font-family:'Times New Roman'; font-size: 10pt; font-family: 'Times New Roman'">The Apply Force Runway function shall transfer the Force functional exchange to the Provide Ground Force and Dampen Spring functions without a loss exceeding 5%.</span></p><p style="margin-top:0pt; margin-bottom:0pt; font-size:10pt"><span style="font-family:'Times New Roman'; font-size: 10pt; font-family: 'Times New Roman'">Rationale: A 5% maximum loss bounds inefficiency in the mechanical load path to keep landing and taxi load calculations within their certified margins.</span></p>
                    */ 
                    @CapellaID { eid = "d2f4e60b-dd37-4f66-a056-a683f5465964"; } 
                    satisfy 'Nose Landing Gear Library'::'Nose Landing Gear'::'PLM Data'::'PLM Requirements'.'Force Transfer Integrity'  by
                        'Physical Architecture'::'Physical Functions'::'Root Physical Function'.'Measure'.'Actuate NLG'.'Apply Force Runway'; 
                     
                }  
                requirement <'REQ-000846/A'> 'Valve Response Time' : 'PLM Requirement Types'::'PlmRequirement'  { 
                    doc /*
                    <p style="margin-top:0pt; margin-bottom:0pt; font-size:10pt"><span style="font-family:'Times New Roman'; font-size: 10pt; font-family: 'Times New Roman'">The NLG Door Selector Valve shall route commanded pressure to the Move Door output within 0.3 seconds of receiving a valid NLG Door command.</span></p><p style="margin-top:0pt; margin-bottom:0pt; font-size:10pt"><span style="font-family:'Times New Roman'; font-size: 10pt; font-family: 'Times New Roman'">Rationale: 0.3 s is allocated from the 8-second Retract and Extend cycle budget (Retract Cycle Time, REQ-000841/A) so door movement completes early enough in the sequence to clear the gear bay before leg retraction begins.</span></p>
                    */ 
                    @CapellaID { eid = "1375c9fb-cf58-4ce6-8480-0061c44aa830"; } 
                    satisfy 'Nose Landing Gear Library'::'Nose Landing Gear'::'PLM Data'::'PLM Requirements'.'Valve Response Time'  by
                        'Physical Architecture'::'Structure'::'Physical System'.'Nose Landing Gear'.'NLG Doors Dump Valve'; 
                     
                }  
            }  
        } 
        package 'SMW Properties' {
            @PackageMeta {
                type = "PropertyValuePkg";
            } 
            @CapellaID { eid = "15a1b09a-512a-4272-b0ef-71e20e701dc9"; } 
            package 'Parameters' {
                @PackageMeta {
                    type = "PropertyValuePkg";
                } 
                @CapellaID { eid = "e7a497d7-0a90-478d-8aab-2c5a409c9085"; } 
                attribute 'Extension Cycle Time (sec)' : PropertyValueGroup { 
                    @CapellaID { eid = "348cfa06-ae9b-4b53-aa44-f3f1aa8a2b34"; } 
                    attribute 'Goal' : FloatPropertyValue  = 8.0 { 
                        @CapellaID { eid = "78a37f96-a676-4152-889f-860ac117bf81"; } 
                    }  
                    attribute 'Min' : FloatPropertyValue  = 0.0 { 
                        @CapellaID { eid = "8c85dcad-2535-417a-8d8a-b8584a1bff2b"; } 
                    }  
                    attribute 'Max' : FloatPropertyValue  = 10.0 { 
                        @CapellaID { eid = "5b32d617-2419-44d9-b60a-f69e4af3d599"; } 
                    }  
                     
                     
                    ref :>> ownedPropertyValues =  ('Goal',
                    'Min',
                    'Max'); 
                }  
                attribute 'Retract Cycle Time (sec)' : PropertyValueGroup { 
                    @CapellaID { eid = "b7fcb104-6afa-4d16-a4e9-02e1c9c51a73"; } 
                    attribute 'Goal' : FloatPropertyValue  = 0.0 { 
                        @CapellaID { eid = "debdedaf-81a5-41cb-a1b5-25eb4e734de8"; } 
                    }  
                    attribute 'Min' : FloatPropertyValue  = 0.0 { 
                        @CapellaID { eid = "5eab7687-a3cb-47db-9e45-ae5740f4598b"; } 
                    }  
                    attribute 'Max' : FloatPropertyValue  = 8.0 { 
                        @CapellaID { eid = "7c35d9cd-35f3-409f-98f3-bb5fea73bea7"; } 
                    }  
                     
                     
                    ref :>> ownedPropertyValues =  ('Goal',
                    'Min',
                    'Max'); 
                }  
            } 
            enum def 'SMW_SYNC_STATUS' :> EnumerationPropertyType  { 
                enum 'SYNC'; 
                enum 'SYNC_DEEP'; 
            }  
            enum def 'SMW_REMOTE_OBJ_KIND' :> EnumerationPropertyType  { 
                enum 'ParamDbl'; 
            }  
        } 
        package 'Operational Analysis' {
            @PackageMeta {
                type = "OperationalAnalysis";
            } 
            @CapellaID { eid = "7f883218-d60e-430b-86b1-8d47f21fd6d8"; } 
            package 'Data' {
                @PackageMeta {
                    type = "DataPkg";
                } 
                @CapellaID { eid = "f4597d15-ee0d-40fc-83d1-79c2be70f652"; } 
            } 
            package 'Interfaces' {
                @PackageMeta {
                    type = "InterfacePkg";
                } 
                @CapellaID { eid = "529ff3b9-7d6f-4ae7-a991-4bc5cf2ede5f"; } 
            } 
            package 'Roles' {
                @PackageMeta {
                    type = "RolePkg";
                } 
                @CapellaID { eid = "77f50c84-5a14-48d7-aacf-8682624dbec1"; } 
            } 
            package 'Operational Activities' {
                @PackageMeta {
                    type = "OperationalActivityPkg";
                } 
                @CapellaID { eid = "59daa2f5-2c84-4560-9558-610ac2ab4397"; } 
                action 'Root Operational Activity' : OperationalActivity  { 
                    @CapellaID { eid = "76725496-81c5-425b-9b67-b8095e14eabc"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> kind = FunctionKind::FUNCTION; 
                    attribute :>> isMaxInclusive = false; 
                    attribute :>> isMinInclusive = false; 
                    attribute :>> isOrdered = false; 
                    attribute :>> isUnique = false; 
                }  
            } 
            package 'Operational Capabilities' {
                @PackageMeta {
                    type = "OperationalCapabilityPkg";
                } 
                @CapellaID { eid = "b67bea40-db7b-4b72-a04d-0be2696bcd9f"; } 
            } 
            package 'Operational Entities' {
                @PackageMeta {
                    type = "EntityPkg";
                } 
                @CapellaID { eid = "dfcc3249-7740-44e4-80ec-9e81a9e7267a"; } 
            } 
        } 
        package 'System Analysis' {
            @PackageMeta {
                type = "SystemAnalysis";
            } 
            @CapellaID { eid = "1ef11e57-2d79-45c2-8987-639782ed6265"; } 
            package 'Data' {
                @PackageMeta {
                    type = "DataPkg";
                } 
                @CapellaID { eid = "5eb5b12a-e7d9-4756-aa48-e32a84b0d1e3"; } 
                package 'Predefined Types' {
                    @PackageMeta {
                        type = "DataPkg";
                    } 
                    @CapellaID { eid = "9ae9db38-fe78-4a04-b3e7-e0bec9dda183"; } 
                } 
            } 
            package 'Interfaces' {
                @PackageMeta {
                    type = "InterfacePkg";
                } 
                @CapellaID { eid = "cfd02f4b-42ef-4f89-863e-ecbae771d2ce"; } 
            } 
            package 'Structure' {
                @PackageMeta {
                    type = "SystemComponentPkg";
                } 
                @CapellaID { eid = "1afb5efc-c2d8-4840-a6c4-e2caaa291bfd"; } 
                part '2efa85e7-0445-4510-a3e7-f274a7362dc6' : CPart :> 'Drone'  { 
                    @CapellaID { eid = "2efa85e7-0445-4510-a3e7-f274a7362dc6"; sid = "d2b60dd0-657b-41ef-88fa-62ad2ed1e88a"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> isMaxInclusive = false; 
                    attribute :>> isMinInclusive = false; 
                    attribute :>> isOrdered = false; 
                    attribute :>> isUnique = false; 
                    constraint '2a54fd7e-42e0-442a-96a2-60478835a589' : CapellaConstraint { 
                        language "capella:linkedText" /*  */
                        @CapellaID { eid = "2a54fd7e-42e0-442a-96a2-60478835a589"; }
                        ref :>> constrainedElements =  ('Nose Landing Gear Library'::'Nose Landing Gear'::'System Analysis'::'Structure'::'2efa85e7-0445-4510-a3e7-f274a7362dc6');
                        
                    } 
                    ref :>> ownedConstraints =  ('2a54fd7e-42e0-442a-96a2-60478835a589'); 
                }  
                part 'Drone' : SystemComponent { 
                    @CapellaID { eid = "e7d8dc7e-f3af-4e15-b006-44f06f746d84"; sid = "f17f94b5-a717-4018-8a61-0ed107f1909f"; } 
                    attribute :>> isAbstract = false; 
                    attribute :>> isActor = false; 
                    attribute :>> isDataComponent = false; 
                    attribute :>> isHuman = false; 
                    port 'PP 1' : PhysicalPort { 
                        @CapellaID { eid = "2a48482e-bbdc-46ab-a536-b7da6bab1530"; sid = "4f232cfe-c7f6-4df0-8fcc-2d56df91affd"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                    }  
                    state 'System State Machine' : StateMachine  { 
                        @CapellaID { eid = "cb1b1cc4-23c0-4853-985a-5535e4f1ebe4"; } 
                        attribute :>> isControlOperator = false; 
                    }  
                    ref :>> ownedStateMachines =  ('System State Machine'); 
                }  
            } 
            constraint 'f841c1a2-1bf3-472a-97c7-010db55a72a5' : CapellaConstraint { 
                @CapellaID { eid = "f841c1a2-1bf3-472a-97c7-010db55a72a5"; sid = "9908151b-5781-4320-9ec5-5d60adb1adf8"; }
                ref :>> constrainedElements =  ('Structure'::'2efa85e7-0445-4510-a3e7-f274a7362dc6');
            } 
            package 'System Functions' {
                @PackageMeta {
                    type = "SystemFunctionPkg";
                } 
                @CapellaID { eid = "7585bf9f-65bf-4b23-9142-d34ec6ee3483"; } 
                action 'Root System Function' : SystemFunction  { 
                    @CapellaID { eid = "6b2d2946-547b-43ce-98e7-17b134d1fdb8"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> kind = FunctionKind::FUNCTION; 
                    attribute :>> isMaxInclusive = false; 
                    attribute :>> isMinInclusive = false; 
                    attribute :>> isOrdered = false; 
                    attribute :>> isUnique = false; 
                     
                }  
            } 
            package 'Missions' {
                @PackageMeta {
                    type = "MissionPkg";
                } 
                @CapellaID { eid = "36115461-8f4b-4d20-ad07-7a26b830268a"; } 
            } 
            package 'Capabilities' {
                @PackageMeta {
                    type = "CapabilityPkg";
                } 
                @CapellaID { eid = "4a517d34-2c92-4cd4-9f7e-825f7034362d"; } 
            } 
        } 
        package 'Logical Architecture' {
            @PackageMeta {
                type = "LogicalArchitecture";
            } 
            @CapellaID { eid = "62f2933f-a2c2-4e9d-911a-627d716250ae"; sid = "62f2933f-a2c2-4e9d-911a-627d716250ae"; } 
            package 'Data' {
                @PackageMeta {
                    type = "DataPkg";
                } 
                @CapellaID { eid = "bb0f60c2-0957-440e-9e21-af1bf9b6b355"; } 
            } 
            package 'Interfaces' {
                @PackageMeta {
                    type = "InterfacePkg";
                } 
                @CapellaID { eid = "78043444-13b8-42d6-b9fa-b9564bf16c4d"; } 
            } 
            constraint '68ed1c83-6d78-4c20-ad4e-8be00bfd60c9' : CapellaConstraint { 
                language "capella:linkedText" /*  */
                @CapellaID { eid = "68ed1c83-6d78-4c20-ad4e-8be00bfd60c9"; sid = "9908151b-5781-4320-9ec5-5d60adb1adf8"; }
                ref :>> constrainedElements =  ('Structure'::'197debd5-87d2-402d-9b61-0f6b2b7194ff');
                
            } 
            dependency 'd565714b-b77e-449e-b778-88ec2fe00ea5'
                from 'Logical Architecture'::'68ed1c83-6d78-4c20-ad4e-8be00bfd60c9'
                to  'System Analysis'::'f841c1a2-1bf3-472a-97c7-010db55a72a5' { 
                @TransfoLink { 
                    @CapellaID { eid = "d565714b-b77e-449e-b778-88ec2fe00ea5"; } 
                }  
            }  
            package 'Logical Functions' {
                @PackageMeta {
                    type = "LogicalFunctionPkg";
                } 
                @CapellaID { eid = "0d511d4d-2d2d-4a61-bc2c-73b15b20dfee"; } 
                action 'Root Logical Function' : LogicalFunction  { 
                    @CapellaID { eid = "f3823690-9709-46ab-91ab-5c006760f55f"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> kind = FunctionKind::FUNCTION; 
                    attribute :>> isMaxInclusive = false; 
                    attribute :>> isMinInclusive = false; 
                    attribute :>> isOrdered = false; 
                    attribute :>> isUnique = false; 
                     
                }  
            } 
            package 'Structure' {
                @PackageMeta {
                    type = "LogicalComponentPkg";
                } 
                @CapellaID { eid = "7e3de60b-e4db-4205-a923-00f6ae4c5b0c"; } 
                part '197debd5-87d2-402d-9b61-0f6b2b7194ff' : CPart :> 'UAV System'  { 
                    @CapellaID { eid = "197debd5-87d2-402d-9b61-0f6b2b7194ff"; sid = "d2b60dd0-657b-41ef-88fa-62ad2ed1e88a"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> isMaxInclusive = false; 
                    attribute :>> isMinInclusive = false; 
                    attribute :>> isOrdered = false; 
                    attribute :>> isUnique = false; 
                }  
                dependency '78ee43ad-3323-4678-bbf1-0e9653850963'
                    from 'Structure'::'197debd5-87d2-402d-9b61-0f6b2b7194ff'
                    to  'System Analysis'::'Structure'::'2efa85e7-0445-4510-a3e7-f274a7362dc6' { 
                    @TransfoLink { 
                        @CapellaID { eid = "78ee43ad-3323-4678-bbf1-0e9653850963"; } 
                    }  
                }  
                part 'UAV System' : LogicalComponent { 
                    @CapellaID { eid = "3bf9effb-6d47-4314-b1b6-21ba50798446"; sid = "f17f94b5-a717-4018-8a61-0ed107f1909f"; } 
                    attribute :>> isAbstract = false; 
                    attribute :>> isActor = false; 
                    attribute :>> isHuman = false; 
                    interface 'be012c1d-4a38-4db7-86ab-27e8f217bbf7' : ComponentExchange 
                        connect source ::> 'Ground Station'.'CP 1'
                        to  target ::> 'Satellite'.'CP 1' { 
                        @CapellaID { eid = "be012c1d-4a38-4db7-86ab-27e8f217bbf7"; } 
                        attribute :>> kind = ComponentExchangeKind::FLOW; 
                        attribute :>> interfaceName = "Ground/Sat Signal"; 
                        attribute :>> isOriented = false; 
                    }  
                    interface '1afa5e35-28f6-4745-8af1-d0908289efe8' : ComponentExchange 
                        connect source ::> 'Satellite'.'CP 2'
                        to  target ::> 'Drone'.'Avionics'.'Communications'.'CP 1' { 
                        @CapellaID { eid = "1afa5e35-28f6-4745-8af1-d0908289efe8"; } 
                        attribute :>> kind = ComponentExchangeKind::FLOW; 
                        attribute :>> interfaceName = "BLOS Signal"; 
                        attribute :>> isOriented = false; 
                    }  
                    interface '0bd855ad-9867-426e-9ff7-891b030eccbe' : ComponentExchange 
                        connect source ::> 'Ground Station'.'CP 2'
                        to  target ::> 'Drone'.'Avionics'.'Communications'.'CP 1' { 
                        @CapellaID { eid = "0bd855ad-9867-426e-9ff7-891b030eccbe"; } 
                        attribute :>> kind = ComponentExchangeKind::FLOW; 
                        attribute :>> interfaceName = "LOS Signal"; 
                        attribute :>> isOriented = false; 
                    }  
                    part '1fe21abb-8db4-4308-a1be-303ea80671f3' : CPart :> 'Satellite'  { 
                        @CapellaID { eid = "1fe21abb-8db4-4308-a1be-303ea80671f3"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                    }  
                    part '933d28e1-1eda-40f2-96a0-633c06bc359f' : CPart :> 'Ground Station'  { 
                        @CapellaID { eid = "933d28e1-1eda-40f2-96a0-633c06bc359f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                    }  
                    part 'f1d7deae-661b-47a9-a8dd-3165ff79efc5' : CPart :> 'Drone'  { 
                        @CapellaID { eid = "f1d7deae-661b-47a9-a8dd-3165ff79efc5"; sid = "f1d7deae-661b-47a9-a8dd-3165ff79efc5"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                    }  
                    port 'PP 1' : PhysicalPort { 
                        @CapellaID { eid = "7fffe81f-b081-4a29-9251-6eec1de6613d"; sid = "4f232cfe-c7f6-4df0-8fcc-2d56df91affd"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part 'a937fc00-a7cf-4b0f-9278-f2e29fcd2dd7' : CPart :> 'Drone BC'  { 
                        @CapellaID { eid = "a937fc00-a7cf-4b0f-9278-f2e29fcd2dd7"; sid = "8e5ac6c7-fec6-4644-ba85-5dae73b66a23"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                    }  
                    part '9e074f7d-11f9-45b2-8f8d-d2f2e73c431c' : CPart :> 'Communication and Navitagation Subsystem'  { 
                        @CapellaID { eid = "9e074f7d-11f9-45b2-8f8d-d2f2e73c431c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                    }  
                    part 'Satellite' : LogicalComponent { 
                        @CapellaID { eid = "ad6469b7-db07-4ca3-846f-c8f453ca1e8c"; } 
                        attribute :>> isAbstract = false; 
                        attribute :>> isActor = false; 
                        attribute :>> isHuman = false; 
                        port 'CP 1' : ComponentPort { 
                            @CapellaID { eid = "e3203b4b-755a-4bd1-846d-4657672e683c"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                        }  
                        port 'CP 2' : ComponentPort { 
                            @CapellaID { eid = "e32782a3-47a2-4439-86b8-06fad38bf71b"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                        }  
                    }  
                    part 'Ground Station' : LogicalComponent { 
                        @CapellaID { eid = "6c5c848e-a499-44ed-8250-92422d22e6ad"; } 
                        attribute :>> isAbstract = false; 
                        attribute :>> isActor = false; 
                        attribute :>> isHuman = false; 
                        port 'CP 1' : ComponentPort { 
                            @CapellaID { eid = "f648aadd-dc79-48ab-b279-e8babf0d42f9"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                        }  
                        port 'CP 2' : ComponentPort { 
                            @CapellaID { eid = "0097225a-d425-4316-9c31-ad318098af00"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                        }  
                        port 'CP 3' : ComponentPort { 
                            @CapellaID { eid = "403750bb-4e36-481c-a925-3bef7f9f35ad"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                        }  
                        port 'CP 4' : ComponentPort { 
                            @CapellaID { eid = "57aeb545-e4aa-4d21-b205-22128e61d390"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                        }  
                    }  
                    part 'Drone' : LogicalComponent { 
                        @CapellaID { eid = "5350efe5-2cdf-493f-891b-f106fb4d99de"; sid = "5350efe5-2cdf-493f-891b-f106fb4d99de"; } 
                        attribute :>> isAbstract = false; 
                        attribute :>> isActor = false; 
                        attribute :>> isHuman = false; 
                        part '94d17f07-4c72-490b-bd10-cc95e8aa6e6a' : CPart :> 'Avionics'  { 
                            @CapellaID { eid = "94d17f07-4c72-490b-bd10-cc95e8aa6e6a"; sid = "94d17f07-4c72-490b-bd10-cc95e8aa6e6a"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                        }  
                        part 'ec3a948c-5f9d-4615-bef1-4ce415c037b7' : CPart :> 'Payload'  { 
                            @CapellaID { eid = "ec3a948c-5f9d-4615-bef1-4ce415c037b7"; sid = "ec3a948c-5f9d-4615-bef1-4ce415c037b7"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                        }  
                        part '989ebd68-beb2-4712-af8a-765fb3e53ab9' : CPart :> 'Vehicle Subsystems'  { 
                            @CapellaID { eid = "989ebd68-beb2-4712-af8a-765fb3e53ab9"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                        }  
                        part '158621a6-4e6d-4bc3-bdf4-d44029f536ed' : CPart :> 'Airframe'  { 
                            @CapellaID { eid = "158621a6-4e6d-4bc3-bdf4-d44029f536ed"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                        }  
                        part '79e8612e-dd14-45bf-8de0-dfb81ef53494' : CPart :> 'Propulsion'  { 
                            @CapellaID { eid = "79e8612e-dd14-45bf-8de0-dfb81ef53494"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                        }  
                        part 'Avionics' : LogicalComponent { 
                            @CapellaID { eid = "5b01336f-8960-48cb-8a5b-51c35588f0dc"; sid = "5b01336f-8960-48cb-8a5b-51c35588f0dc"; } 
                            attribute :>> isAbstract = false; 
                            attribute :>> isActor = false; 
                            attribute :>> isHuman = false; 
                            part 'fc61ecd3-0df0-4982-8301-b1fd219d4099' : CPart :> 'Mission Data CPU'  { 
                                @CapellaID { eid = "fc61ecd3-0df0-4982-8301-b1fd219d4099"; sid = "fc61ecd3-0df0-4982-8301-b1fd219d4099"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part 'fd20b82a-6f53-49e3-8b0a-dd980ff6723e' : CPart :> 'Communications'  { 
                                @CapellaID { eid = "fd20b82a-6f53-49e3-8b0a-dd980ff6723e"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part '6d51798a-9377-47da-a518-127a43870ff2' : CPart :> 'Nav / Guidance'  { 
                                @CapellaID { eid = "6d51798a-9377-47da-a518-127a43870ff2"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part '63efc07b-2535-4cb9-86d5-1cfb8daf1abb' : CPart :> 'Auto Flight Control'  { 
                                @CapellaID { eid = "63efc07b-2535-4cb9-86d5-1cfb8daf1abb"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part '73d90af6-d81b-47fb-ac9d-0d9c848abc87' : CPart :> 'Health Monitoring'  { 
                                @CapellaID { eid = "73d90af6-d81b-47fb-ac9d-0d9c848abc87"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part '301b47e9-e3a6-441e-b541-d17dbf7e6f58' : CPart :> 'Stores Management'  { 
                                @CapellaID { eid = "301b47e9-e3a6-441e-b541-d17dbf7e6f58"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part 'Mission Data CPU' : LogicalComponent { 
                                @CapellaID { eid = "592aa5c1-e157-4d39-ad4e-95cc4d0e6e68"; sid = "592aa5c1-e157-4d39-ad4e-95cc4d0e6e68"; } 
                                attribute :>> isAbstract = false; 
                                attribute :>> isActor = false; 
                                attribute :>> isHuman = false; 
                            }  
                            part 'Communications' : LogicalComponent { 
                                @CapellaID { eid = "7ec6e9bb-35e9-41b2-93af-db419b38dd76"; } 
                                attribute :>> isAbstract = false; 
                                attribute :>> isActor = false; 
                                attribute :>> isHuman = false; 
                                port 'CP 1' : ComponentPort { 
                                    @CapellaID { eid = "2708b19b-cd4c-4877-918e-7ee1bcdfd6bb"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                }  
                            }  
                            part 'Nav / Guidance' : LogicalComponent { 
                                @CapellaID { eid = "754f7c36-7547-4dd8-95c1-6dbe4014530b"; } 
                                attribute :>> isAbstract = false; 
                                attribute :>> isActor = false; 
                                attribute :>> isHuman = false; 
                            }  
                            part 'Auto Flight Control' : LogicalComponent { 
                                @CapellaID { eid = "fa4ec9b0-2a9b-4620-b355-8beda15532fd"; } 
                                attribute :>> isAbstract = false; 
                                attribute :>> isActor = false; 
                                attribute :>> isHuman = false; 
                            }  
                            part 'Health Monitoring' : LogicalComponent { 
                                @CapellaID { eid = "0397ab64-40e3-4de2-8f31-7061d788ddb8"; } 
                                attribute :>> isAbstract = false; 
                                attribute :>> isActor = false; 
                                attribute :>> isHuman = false; 
                            }  
                            part 'Stores Management' : LogicalComponent { 
                                @CapellaID { eid = "0e9ad734-8e4c-40db-9136-68a9d7abe2a8"; } 
                                attribute :>> isAbstract = false; 
                                attribute :>> isActor = false; 
                                attribute :>> isHuman = false; 
                            }  
                            ref :>> ownedLogicalComponents =  ('Mission Data CPU',
                            'Communications',
                            'Nav / Guidance',
                            'Auto Flight Control',
                            'Health Monitoring',
                            'Stores Management'); 
                        }  
                        part 'Payload' : LogicalComponent { 
                            @CapellaID { eid = "69b9b5c6-ad34-46e9-bf3c-042bf374b790"; sid = "69b9b5c6-ad34-46e9-bf3c-042bf374b790"; } 
                            attribute :>> isAbstract = false; 
                            attribute :>> isActor = false; 
                            attribute :>> isHuman = false; 
                            part '9dc13a3b-f6ad-45f0-825c-03793818283b' : CPart :> 'Sensor Pkg'  { 
                                @CapellaID { eid = "9dc13a3b-f6ad-45f0-825c-03793818283b"; sid = "9dc13a3b-f6ad-45f0-825c-03793818283b"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part 'Sensor Pkg' : LogicalComponent { 
                                @CapellaID { eid = "d60141a4-c40a-40ed-890b-10d5227fcdc8"; sid = "d60141a4-c40a-40ed-890b-10d5227fcdc8"; } 
                                attribute :>> isAbstract = false; 
                                attribute :>> isActor = false; 
                                attribute :>> isHuman = false; 
                            }  
                            ref :>> ownedLogicalComponents =  ('Sensor Pkg'); 
                        }  
                        part 'Vehicle Subsystems' : LogicalComponent { 
                            @CapellaID { eid = "b59eab16-52ee-4ef9-a328-c61f684ddc80"; } 
                            attribute :>> isAbstract = false; 
                            attribute :>> isActor = false; 
                            attribute :>> isHuman = false; 
                            part 'b58a4d31-181f-48ca-a7bb-0a7a6b1af043' : CPart :> 'Flight Control'  { 
                                @CapellaID { eid = "b58a4d31-181f-48ca-a7bb-0a7a6b1af043"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part '7434da43-877e-4410-bcb3-6040580cb1b1' : CPart :> 'Environmental Control'  { 
                                @CapellaID { eid = "7434da43-877e-4410-bcb3-6040580cb1b1"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part '87e8d62c-f2c7-4110-906d-67a05b9ff989' : CPart :> 'Landing Gear Subsystem'  { 
                                @CapellaID { eid = "87e8d62c-f2c7-4110-906d-67a05b9ff989"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part '9f9353c3-8032-41ef-b523-d1ceae0aaa73' : CPart :> 'Fuel and Power System'  { 
                                @CapellaID { eid = "9f9353c3-8032-41ef-b523-d1ceae0aaa73"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part 'af487892-f9fe-467e-8172-3c03dab78eeb' : CPart :> 'Electrical'  { 
                                @CapellaID { eid = "af487892-f9fe-467e-8172-3c03dab78eeb"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part '0ed5562d-4d8a-4d8e-b9ec-4ad13e3fab8e' : CPart :> 'Fuel'  { 
                                @CapellaID { eid = "0ed5562d-4d8a-4d8e-b9ec-4ad13e3fab8e"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part '73f4a71d-269d-4aa6-bc94-6613a5a17c0c' : CPart :> 'Software'  { 
                                @CapellaID { eid = "73f4a71d-269d-4aa6-bc94-6613a5a17c0c"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part '6846da03-b57a-4110-bce3-e32f2698ffdb' : CPart :> 'Hydraulic System'  { 
                                @CapellaID { eid = "6846da03-b57a-4110-bce3-e32f2698ffdb"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part 'Flight Control' : LogicalComponent { 
                                @CapellaID { eid = "66912732-403a-47da-b005-cfb145209303"; } 
                                attribute :>> isAbstract = false; 
                                attribute :>> isActor = false; 
                                attribute :>> isHuman = false; 
                            }  
                            part 'Environmental Control' : LogicalComponent { 
                                @CapellaID { eid = "c5c6c4f5-6b5b-4bad-8115-37e33cbb9231"; } 
                                attribute :>> isAbstract = false; 
                                attribute :>> isActor = false; 
                                attribute :>> isHuman = false; 
                            }  
                            part 'Landing Gear Subsystem' : LogicalComponent { 
                                @CapellaID { eid = "185816f8-7696-47dc-a54f-99e897e60eca"; } 
                                attribute :>> isAbstract = false; 
                                attribute :>> isActor = false; 
                                attribute :>> isHuman = false; 
                                part '1d5b7b3f-fdd1-47aa-b8f7-0cace4d71687' : CPart :> 'Extension Retraction Lever'  { 
                                    @CapellaID { eid = "1d5b7b3f-fdd1-47aa-b8f7-0cace4d71687"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                part '2c0e628e-3d25-4bb9-b895-f6647aa77a98' : CPart :> 'Landing Gear'  { 
                                    @CapellaID { eid = "2c0e628e-3d25-4bb9-b895-f6647aa77a98"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                part '4901f5e8-bffa-4bcf-8102-fe8b39ab5eb5' : CPart :> 'Landing Gear Control and Indication Computer'  { 
                                    @CapellaID { eid = "4901f5e8-bffa-4bcf-8102-fe8b39ab5eb5"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                part 'Extension Retraction Lever' : LogicalComponent { 
                                    @CapellaID { eid = "e0a63d8d-b3ee-4118-832e-df6bad6591df"; } 
                                    attribute :>> isAbstract = false; 
                                    attribute :>> isActor = false; 
                                    attribute :>> isHuman = false; 
                                }  
                                part 'Landing Gear' : LogicalComponent { 
                                    @CapellaID { eid = "fefcded6-d59a-429e-ae59-a0c86e8be42d"; } 
                                    attribute :>> isAbstract = false; 
                                    attribute :>> isActor = false; 
                                    attribute :>> isHuman = false; 
                                    part '182b540e-e4c7-4dfc-a983-e96c7ce2e8cf' : CPart :> 'NLG'  { 
                                        @CapellaID { eid = "182b540e-e4c7-4dfc-a983-e96c7ce2e8cf"; } 
                                        attribute :>> aggregationKind = AggregationKind::UNSET; 
                                        attribute :>> isFinal = false; 
                                        attribute :>> isAbstract = false; 
                                        attribute :>> isDerived = false; 
                                        attribute :>> isPartOfKey = false; 
                                        attribute :>> isReadOnly = false; 
                                        attribute :>> isStatic = false; 
                                        attribute :>> isMaxInclusive = false; 
                                        attribute :>> isMinInclusive = false; 
                                        attribute :>> isOrdered = false; 
                                        attribute :>> isUnique = false; 
                                    }  
                                    part '187c3b7d-d924-4663-a7b9-d5754b641fcc' : CPart :> 'ML'  { 
                                        @CapellaID { eid = "187c3b7d-d924-4663-a7b9-d5754b641fcc"; } 
                                        attribute :>> aggregationKind = AggregationKind::UNSET; 
                                        attribute :>> isFinal = false; 
                                        attribute :>> isAbstract = false; 
                                        attribute :>> isDerived = false; 
                                        attribute :>> isPartOfKey = false; 
                                        attribute :>> isReadOnly = false; 
                                        attribute :>> isStatic = false; 
                                        attribute :>> isMaxInclusive = false; 
                                        attribute :>> isMinInclusive = false; 
                                        attribute :>> isOrdered = false; 
                                        attribute :>> isUnique = false; 
                                    }  
                                    part 'NLG' : LogicalComponent { 
                                        @CapellaID { eid = "d9a8c47d-9b40-447a-af0f-b55587b29fed"; } 
                                        attribute :>> isAbstract = false; 
                                        attribute :>> isActor = false; 
                                        attribute :>> isHuman = false; 
                                    }  
                                    part 'ML' : LogicalComponent { 
                                        @CapellaID { eid = "c1031f70-9a0c-4a08-af90-9a0dd4ba9f82"; } 
                                        attribute :>> isAbstract = false; 
                                        attribute :>> isActor = false; 
                                        attribute :>> isHuman = false; 
                                        part '8eea8412-04c7-48fc-a8be-007d66fecf35' : CPart :> 'RMG'  { 
                                            @CapellaID { eid = "8eea8412-04c7-48fc-a8be-007d66fecf35"; } 
                                            attribute :>> aggregationKind = AggregationKind::UNSET; 
                                            attribute :>> isFinal = false; 
                                            attribute :>> isAbstract = false; 
                                            attribute :>> isDerived = false; 
                                            attribute :>> isPartOfKey = false; 
                                            attribute :>> isReadOnly = false; 
                                            attribute :>> isStatic = false; 
                                            attribute :>> isMaxInclusive = false; 
                                            attribute :>> isMinInclusive = false; 
                                            attribute :>> isOrdered = false; 
                                            attribute :>> isUnique = false; 
                                        }  
                                        part '36802883-9816-454e-abd5-86fa1be3043a' : CPart :> 'LMG'  { 
                                            @CapellaID { eid = "36802883-9816-454e-abd5-86fa1be3043a"; } 
                                            attribute :>> aggregationKind = AggregationKind::UNSET; 
                                            attribute :>> isFinal = false; 
                                            attribute :>> isAbstract = false; 
                                            attribute :>> isDerived = false; 
                                            attribute :>> isPartOfKey = false; 
                                            attribute :>> isReadOnly = false; 
                                            attribute :>> isStatic = false; 
                                            attribute :>> isMaxInclusive = false; 
                                            attribute :>> isMinInclusive = false; 
                                            attribute :>> isOrdered = false; 
                                            attribute :>> isUnique = false; 
                                        }  
                                        part 'RMG' : LogicalComponent { 
                                            @CapellaID { eid = "58afb717-aec1-4fc2-a56b-c4fb5d8e5195"; } 
                                            attribute :>> isAbstract = false; 
                                            attribute :>> isActor = false; 
                                            attribute :>> isHuman = false; 
                                        }  
                                        part 'LMG' : LogicalComponent { 
                                            @CapellaID { eid = "b64b36bc-cd0d-45b7-90d0-46b9d5ecfc71"; } 
                                            attribute :>> isAbstract = false; 
                                            attribute :>> isActor = false; 
                                            attribute :>> isHuman = false; 
                                        }  
                                        ref :>> ownedLogicalComponents =  ('RMG',
                                        'LMG'); 
                                    }  
                                    ref :>> ownedLogicalComponents =  ('NLG',
                                    'ML'); 
                                }  
                                part 'Landing Gear Control and Indication Computer' : LogicalComponent { 
                                    @CapellaID { eid = "dd72f4a0-de68-4d37-9ad2-1783c88393a1"; } 
                                    attribute :>> isAbstract = false; 
                                    attribute :>> isActor = false; 
                                    attribute :>> isHuman = false; 
                                }  
                                ref :>> ownedLogicalComponents =  ('Extension Retraction Lever',
                                'Landing Gear',
                                'Landing Gear Control and Indication Computer'); 
                            }  
                            part 'Fuel and Power System' : LogicalComponent { 
                                @CapellaID { eid = "6835f2de-bc29-42b2-b60d-e8eb57ed7d18"; } 
                                attribute :>> isAbstract = false; 
                                attribute :>> isActor = false; 
                                attribute :>> isHuman = false; 
                            }  
                            part 'Electrical' : LogicalComponent { 
                                @CapellaID { eid = "e7cc803d-3f44-4ebe-834d-a83f868e1b72"; } 
                                attribute :>> isAbstract = false; 
                                attribute :>> isActor = false; 
                                attribute :>> isHuman = false; 
                            }  
                            part 'Fuel' : LogicalComponent { 
                                @CapellaID { eid = "56eada3d-9c1c-409f-bc38-f5efedbf01d3"; } 
                                attribute :>> isAbstract = false; 
                                attribute :>> isActor = false; 
                                attribute :>> isHuman = false; 
                            }  
                            part 'Software' : LogicalComponent { 
                                @CapellaID { eid = "39c8b889-73c8-452a-b82a-a3d1616a0416"; } 
                                attribute :>> isAbstract = false; 
                                attribute :>> isActor = false; 
                                attribute :>> isHuman = false; 
                            }  
                            part 'Hydraulic System' : LogicalComponent { 
                                @CapellaID { eid = "2c68409e-da07-4179-9e86-3a9694bfccb7"; } 
                                attribute :>> isAbstract = false; 
                                attribute :>> isActor = false; 
                                attribute :>> isHuman = false; 
                            }  
                            ref :>> ownedLogicalComponents =  ('Flight Control',
                            'Environmental Control',
                            'Landing Gear Subsystem',
                            'Fuel and Power System',
                            'Electrical',
                            'Fuel',
                            'Software',
                            'Hydraulic System'); 
                        }  
                        part 'Airframe' : LogicalComponent { 
                            @CapellaID { eid = "cb98b001-d014-4273-b082-8c979115c456"; } 
                            attribute :>> isAbstract = false; 
                            attribute :>> isActor = false; 
                            attribute :>> isHuman = false; 
                            part '05b497c4-876e-4fc1-86a8-f724bd86564a' : CPart :> 'Fuselage'  { 
                                @CapellaID { eid = "05b497c4-876e-4fc1-86a8-f724bd86564a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part 'be6c29aa-5b92-4583-8098-4689dc3607b4' : CPart :> 'Empennage'  { 
                                @CapellaID { eid = "be6c29aa-5b92-4583-8098-4689dc3607b4"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part '3471d182-7507-45d7-9997-141a2e48bba2' : CPart :> 'Wing'  { 
                                @CapellaID { eid = "3471d182-7507-45d7-9997-141a2e48bba2"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part 'Fuselage' : LogicalComponent { 
                                @CapellaID { eid = "87fe67eb-a11a-4183-b13f-cb419ffd9a54"; } 
                                attribute :>> isAbstract = false; 
                                attribute :>> isActor = false; 
                                attribute :>> isHuman = false; 
                            }  
                            part 'Empennage' : LogicalComponent { 
                                @CapellaID { eid = "831086b2-5dcf-431f-b92d-48d3446edb22"; } 
                                attribute :>> isAbstract = false; 
                                attribute :>> isActor = false; 
                                attribute :>> isHuman = false; 
                            }  
                            part 'Wing' : LogicalComponent { 
                                @CapellaID { eid = "be880ae6-bfca-4804-906a-632d13651311"; } 
                                attribute :>> isAbstract = false; 
                                attribute :>> isActor = false; 
                                attribute :>> isHuman = false; 
                                part 'bc7673df-9fe7-42d5-9190-832f6c967e09' : CPart :> 'Winglet'  { 
                                    @CapellaID { eid = "bc7673df-9fe7-42d5-9190-832f6c967e09"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                part 'Winglet' : LogicalComponent { 
                                    @CapellaID { eid = "2a5909c1-f33a-4b39-a4f9-6e53cc75830d"; } 
                                    attribute :>> isAbstract = false; 
                                    attribute :>> isActor = false; 
                                    attribute :>> isHuman = false; 
                                }  
                                ref :>> ownedLogicalComponents =  ('Winglet'); 
                            }  
                            ref :>> ownedLogicalComponents =  ('Fuselage',
                            'Empennage',
                            'Wing'); 
                        }  
                        part 'Propulsion' : LogicalComponent { 
                            @CapellaID { eid = "d93040c0-6a41-4d3f-b6c6-cbb04a2c4db0"; } 
                            attribute :>> isAbstract = false; 
                            attribute :>> isActor = false; 
                            attribute :>> isHuman = false; 
                            part '64d24d72-dde4-4d98-b53f-10766df2ca02' : CPart :> 'Engine'  { 
                                @CapellaID { eid = "64d24d72-dde4-4d98-b53f-10766df2ca02"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            part 'Engine' : LogicalComponent { 
                                @CapellaID { eid = "4f396686-311c-4b59-a971-1c5456e962f8"; } 
                                attribute :>> isAbstract = false; 
                                attribute :>> isActor = false; 
                                attribute :>> isHuman = false; 
                            }  
                            ref :>> ownedLogicalComponents =  ('Engine'); 
                        }  
                        ref :>> ownedLogicalComponents =  ('Avionics',
                        'Payload',
                        'Vehicle Subsystems',
                        'Airframe',
                        'Propulsion'); 
                    }  
                    part 'Drone BC' : LogicalComponent { 
                        @CapellaID { eid = "27b3b718-251c-49c0-8f53-f155feb05435"; sid = "b63625d9-80bd-456d-b13b-b56f3933cbbd"; } 
                        attribute :>> isAbstract = false; 
                        attribute :>> isActor = false; 
                        attribute :>> isHuman = false; 
                    }  
                    part 'Communication and Navitagation Subsystem' : LogicalComponent { 
                        @CapellaID { eid = "56beee67-dce2-403c-8d52-727a6ea007db"; } 
                        attribute :>> isAbstract = false; 
                        attribute :>> isActor = false; 
                        attribute :>> isHuman = false; 
                    }  
                    ref :>> ownedComponentExchanges =  ('be012c1d-4a38-4db7-86ab-27e8f217bbf7',
                    '1afa5e35-28f6-4745-8af1-d0908289efe8',
                    '0bd855ad-9867-426e-9ff7-891b030eccbe'); 
                    ref :>> ownedLogicalComponents =  ('Satellite',
                    'Ground Station',
                    'Drone',
                    'Drone BC',
                    'Communication and Navitagation Subsystem'); 
                     
                }  
            } 
            package 'Capabilities' {
                @PackageMeta {
                    type = "CapabilityRealizationPkg";
                } 
                @CapellaID { eid = "95f34fb6-40ff-401e-a83b-08cc32f5c228"; } 
            } 
        } 
        package 'Physical Architecture' {
            @PackageMeta {
                type = "PhysicalArchitecture";
            } 
            @CapellaID { eid = "a999fe77-97b2-4580-aac4-7c7f1f9c4a55"; sid = "a999fe77-97b2-4580-aac4-7c7f1f9c4a55"; } 
            package 'Data' {
                @PackageMeta {
                    type = "DataPkg";
                } 
                @CapellaID { eid = "ddb9b7ae-06c1-431c-a6de-7200194ca6b7"; } 
                attribute 'BUSTYPE' : IntegerPropertyValue  = 0 { 
                    @CapellaID { eid = "ab441b9c-2dad-45a0-8706-bd4bc44d9607"; } 
                }  
            } 
            package 'Interfaces' {
                @PackageMeta {
                    type = "InterfacePkg";
                } 
                @CapellaID { eid = "a5749742-1b51-44fd-a6af-361396eb6b90"; } 
            } 
            package 'Structure' {
                @PackageMeta {
                    type = "PhysicalComponentPkg";
                } 
                @CapellaID { eid = "d70b51ab-c529-42d0-afa8-fc14a9357bbb"; } 
                part '8a14bcc0-976c-4894-9e70-773175689d47' : CPart :> 'Physical System'  { 
                    @CapellaID { eid = "8a14bcc0-976c-4894-9e70-773175689d47"; sid = "8a14bcc0-976c-4894-9e70-773175689d47"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> isMaxInclusive = false; 
                    attribute :>> isMinInclusive = false; 
                    attribute :>> isOrdered = false; 
                    attribute :>> isUnique = false; 
                     
                }  
                part '06ffec5b-b690-4fe2-a6e2-09d1f6b2451e' : CPart :> 'Operator/Pilot'  { 
                    @CapellaID { eid = "06ffec5b-b690-4fe2-a6e2-09d1f6b2451e"; sid = "06ffec5b-b690-4fe2-a6e2-09d1f6b2451e"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> isMaxInclusive = false; 
                    attribute :>> isMinInclusive = false; 
                    attribute :>> isOrdered = false; 
                    attribute :>> isUnique = false; 
                     
                }  
                part '918cac65-eb73-44de-b287-6fbcb88f2c4d' : CPart :> 'Command &amp; Control'  { 
                    @CapellaID { eid = "918cac65-eb73-44de-b287-6fbcb88f2c4d"; sid = "918cac65-eb73-44de-b287-6fbcb88f2c4d"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> isMaxInclusive = false; 
                    attribute :>> isMinInclusive = false; 
                    attribute :>> isOrdered = false; 
                    attribute :>> isUnique = false; 
                     
                }  
                part '5c6e2103-da9f-4cd3-9116-56c7c9a630bc' : CPart :> 'Persons In Need'  { 
                    @CapellaID { eid = "5c6e2103-da9f-4cd3-9116-56c7c9a630bc"; sid = "5c6e2103-da9f-4cd3-9116-56c7c9a630bc"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> isMaxInclusive = false; 
                    attribute :>> isMinInclusive = false; 
                    attribute :>> isOrdered = false; 
                    attribute :>> isUnique = false; 
                     
                }  
                part '98ea0161-a156-4025-8a6d-9a1468d63cd4' : CPart :> 'SatCom'  { 
                    @CapellaID { eid = "98ea0161-a156-4025-8a6d-9a1468d63cd4"; sid = "12173277-d8c2-4861-940d-346482adf2dc"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> isMaxInclusive = false; 
                    attribute :>> isMinInclusive = false; 
                    attribute :>> isOrdered = false; 
                    attribute :>> isUnique = false; 
                     
                }  
                part 'd5f3c8a8-1b10-49c1-8551-50a66dde3da8' : CPart :> 'Central Command'  { 
                    @CapellaID { eid = "d5f3c8a8-1b10-49c1-8551-50a66dde3da8"; sid = "cb86b2cb-a871-4e58-ac06-a56aa3ede2f2"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> isMaxInclusive = false; 
                    attribute :>> isMinInclusive = false; 
                    attribute :>> isOrdered = false; 
                    attribute :>> isUnique = false; 
                     
                }  
                part 'e4949d9a-9d1b-4ec9-86d0-d85e2a87b684' : CPart :> 'Onsite Personnel'  { 
                    @CapellaID { eid = "e4949d9a-9d1b-4ec9-86d0-d85e2a87b684"; sid = "e4949d9a-9d1b-4ec9-86d0-d85e2a87b684"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> isMaxInclusive = false; 
                    attribute :>> isMinInclusive = false; 
                    attribute :>> isOrdered = false; 
                    attribute :>> isUnique = false; 
                     
                }  
                part 'b724c579-edb3-40dd-a11f-4da680dd353c' : CPart :> 'Distressed Location'  { 
                    @CapellaID { eid = "b724c579-edb3-40dd-a11f-4da680dd353c"; sid = "7ab81758-1b78-48f7-bad9-72ba5bc4b4e3"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> isMaxInclusive = false; 
                    attribute :>> isMinInclusive = false; 
                    attribute :>> isOrdered = false; 
                    attribute :>> isUnique = false; 
                     
                }  
                part '3e2377c1-0aff-4e45-b637-fb1ea053a6ce' : CPart :> 'On SIte Personnel'  { 
                    @CapellaID { eid = "3e2377c1-0aff-4e45-b637-fb1ea053a6ce"; sid = "b114b343-b5b3-4710-a229-5cdc0360a12e"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> isMaxInclusive = false; 
                    attribute :>> isMinInclusive = false; 
                    attribute :>> isOrdered = false; 
                    attribute :>> isUnique = false; 
                     
                }  
                part '85d7f355-6e34-4438-8e24-4ee9e3d4583a' : CPart :> 'Runway'  { 
                    @CapellaID { eid = "85d7f355-6e34-4438-8e24-4ee9e3d4583a"; sid = "85d7f355-6e34-4438-8e24-4ee9e3d4583a"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> isMaxInclusive = false; 
                    attribute :>> isMinInclusive = false; 
                    attribute :>> isOrdered = false; 
                    attribute :>> isUnique = false; 
                     
                }  
                part 'fe7159f0-44c7-422b-85ec-ddfa7e2374ba' : CPart :> 'Environment'  { 
                    @CapellaID { eid = "fe7159f0-44c7-422b-85ec-ddfa7e2374ba"; sid = "fe7159f0-44c7-422b-85ec-ddfa7e2374ba"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> isMaxInclusive = false; 
                    attribute :>> isMinInclusive = false; 
                    attribute :>> isOrdered = false; 
                    attribute :>> isUnique = false; 
                     
                }  
                constraint 'f86679b4-fb09-479f-aea1-009e6a109067' : CapellaConstraint { 
                    language "capella:linkedText" /*  */
                    @CapellaID { eid = "f86679b4-fb09-479f-aea1-009e6a109067"; sid = "9908151b-5781-4320-9ec5-5d60adb1adf8"; }
                    ref :>> constrainedElements =  ('Physical System'.'958779f0-af8e-47c2-bbce-87d0126b7d11');
                    
                } 
                constraint 'f3db0ad5-471d-48a5-af99-8a4108e1a0fa' : CapellaConstraint { 
                    language "capella:linkedText" /*  */
                    @CapellaID { eid = "f3db0ad5-471d-48a5-af99-8a4108e1a0fa"; }
                    
                } 
                constraint '3dd05e62-3ad9-4b81-a657-c7bdc34290b1' : CapellaConstraint { 
                    language "capella:linkedText" /*  */
                    @CapellaID { eid = "3dd05e62-3ad9-4b81-a657-c7bdc34290b1"; }
                    
                } 
                interface 'b6519a0d-336b-4d61-9394-f6e97655d0c8' : PhysicalLink 
                    connect sourcePhysicalPort ::> 'Physical System'.'Drone'.'PP 1'
                    to targetPhysicalPort ::> 'SatCom'.'PP 4' {
                    @CapellaID { eid = "b6519a0d-336b-4d61-9394-f6e97655d0c8"; sid = "8bb27527-0f91-465c-9e6b-2e4286b4fe47"; } 
                    attribute :>> interfaceName = "SATCOM"; 
                     
                }  
                interface '7ebe0718-30f3-4587-974c-3851c9390e3b' : PhysicalLink 
                    connect sourcePhysicalPort ::> 'SatCom'.'PP 4'
                    to targetPhysicalPort ::> 'Physical System'.'COM LInk'.'PP 2' {
                    @CapellaID { eid = "7ebe0718-30f3-4587-974c-3851c9390e3b"; } 
                    attribute :>> interfaceName = "SAT Com"; 
                     
                }  
                interface 'fb05e91c-9be6-4ca7-ab21-7d40ac641dc3' : PhysicalLink 
                    connect sourcePhysicalPort ::> 'SatCom'.'PP 2'
                    to targetPhysicalPort ::> 'Operator/Pilot'.'PP 3' {
                    @CapellaID { eid = "fb05e91c-9be6-4ca7-ab21-7d40ac641dc3"; } 
                    attribute :>> interfaceName = "Sat Com"; 
                     
                }  
                interface '27359dce-a8a9-42ab-a83d-a84178aa7fc8' : PhysicalLink 
                    connect sourcePhysicalPort ::> 'SatCom'.'PP 3'
                    to targetPhysicalPort ::> 'Onsite Personnel'.'PP 1' {
                    @CapellaID { eid = "27359dce-a8a9-42ab-a83d-a84178aa7fc8"; } 
                    attribute :>> interfaceName = "SAT COM"; 
                     
                }  
                interface '685987b9-43ce-40b4-a7c3-3328689dd74a' : PhysicalLink 
                    connect sourcePhysicalPort ::> 'SatCom'.'PP 5'
                    to targetPhysicalPort ::> 'Central Command'.'PP 1' {
                    @CapellaID { eid = "685987b9-43ce-40b4-a7c3-3328689dd74a"; } 
                    attribute :>> interfaceName = "SAT COm"; 
                     
                }  
                interface '993b0f9b-2bd3-46aa-b190-34e98545d2f4' : PhysicalLink 
                    connect sourcePhysicalPort ::> 'Physical System'.'FLIR'.'PP 2'
                    to targetPhysicalPort ::> 'Distressed Location'.'PP 1' {
                    @CapellaID { eid = "993b0f9b-2bd3-46aa-b190-34e98545d2f4"; sid = "993b0f9b-2bd3-46aa-b190-34e98545d2f4"; } 
                    attribute :>> interfaceName = "D-DL"; 
                     
                }  
                interface '6be58646-9808-48e9-b9b2-88692e119ded' : PhysicalLink 
                    connect sourcePhysicalPort ::> 'Physical System'.'FLIR'.'PP 3'
                    to targetPhysicalPort ::> 'Persons In Need'.'PP 1' {
                    @CapellaID { eid = "6be58646-9808-48e9-b9b2-88692e119ded"; sid = "6be58646-9808-48e9-b9b2-88692e119ded"; } 
                    attribute :>> interfaceName = "D-PL"; 
                     
                }  
                interface '03befdce-fc5c-4e27-814e-b2b254464fe7' : PhysicalLink 
                    connect sourcePhysicalPort ::> 'Physical System'.'Braking Hydralulic Subsystem'.'Accumulator '.'PP 2'
                    to targetPhysicalPort ::> 'Physical System'.'Braking Hydralulic Subsystem'.'Junction'.'PP 2' {
                    @CapellaID { eid = "03befdce-fc5c-4e27-814e-b2b254464fe7"; } 
                    attribute :>> interfaceName = "Fluid"; 
                     
                }  
                interface '7c529304-0f71-4aa6-abb8-039553a7fa25' : PhysicalLink 
                    connect sourcePhysicalPort ::> 'Physical System'.'Braking Hydralulic Subsystem'.'Selector Valve'.'PP 2'
                    to targetPhysicalPort ::> 'Physical System'.'Braking Hydralulic Subsystem'.'Junction'.'PP 1' {
                    @CapellaID { eid = "7c529304-0f71-4aa6-abb8-039553a7fa25"; } 
                    attribute :>> interfaceName = "Fluid"; 
                     
                     
                }  
                interface '71d60aed-3891-420e-b7bb-26dd9b5f9ce0' : PhysicalLink 
                    connect sourcePhysicalPort ::> 'Physical System'.'Nose Landing Gear'.'NLG Wheel Housing and Assembly'.'PP 5'
                    to targetPhysicalPort ::> 'Runway'.'PP 1' {
                    @CapellaID { eid = "71d60aed-3891-420e-b7bb-26dd9b5f9ce0"; sid = "71d60aed-3891-420e-b7bb-26dd9b5f9ce0"; } 
                    attribute :>> interfaceName = "NLG to Runway"; 
                     
                     
                }  
                interface '1374f171-0935-44cd-8460-b1652c21130c' : PhysicalLink 
                    connect sourcePhysicalPort ::> 'Operator/Pilot'.'PP 6'
                    to targetPhysicalPort ::> 'Physical System'.'Pilot Interface'.'PP 1' {
                    @CapellaID { eid = "1374f171-0935-44cd-8460-b1652c21130c"; } 
                    attribute :>> interfaceName = "PL 11"; 
                     
                }  
                interface '77fa560a-fb55-4b72-a8bf-cdb5435db186' : PhysicalLink 
                    connect sourcePhysicalPort ::> 'Operator/Pilot'.'PP 7'
                    to targetPhysicalPort ::> 'Physical System'.'Pilot Interface'.'PP 2' {
                    @CapellaID { eid = "77fa560a-fb55-4b72-a8bf-cdb5435db186"; } 
                    attribute :>> interfaceName = "PL 12"; 
                     
                }  
                interface '83eb48fa-8838-47c7-a92e-0e42f448f923' : PhysicalLink 
                    connect sourcePhysicalPort ::> 'Operator/Pilot'.'PP 8'
                    to targetPhysicalPort ::> 'Physical System'.'Pilot Interface'.'PP 3' {
                    @CapellaID { eid = "83eb48fa-8838-47c7-a92e-0e42f448f923"; } 
                    attribute :>> interfaceName = "PL 13"; 
                     
                }  
                dependency 'f9f16f35-9ad6-4c38-8ce9-cc8f78012ce3'
                    from 'Structure'::'f86679b4-fb09-479f-aea1-009e6a109067'
                    to  'Logical Architecture'::'68ed1c83-6d78-4c20-ad4e-8be00bfd60c9' { 
                    @TransfoLink { 
                        @CapellaID { eid = "f9f16f35-9ad6-4c38-8ce9-cc8f78012ce3"; } 
                    }  
                }  
                part 'Physical System' : PhysicalComponent { 
                    @CapellaID { eid = "3f63e635-d46d-4836-93cf-daa5f8a02a4a"; sid = "3f63e635-d46d-4836-93cf-daa5f8a02a4a"; } 
                    attribute :>> isAbstract = false; 
                    attribute :>> isActor = false; 
                    attribute :>> isHuman = false; 
                    attribute :>> kind = PhysicalComponentKind::UNSET; 
                    attribute :>> nature = PhysicalComponentNature::UNSET; 
                    dependency 'e970b3de-59d1-4d6a-b5ea-223ad73e7794'
                        from '958779f0-af8e-47c2-bbce-87d0126b7d11'
                        to  'Logical Architecture'::'Structure'::'197debd5-87d2-402d-9b61-0f6b2b7194ff' { 
                        @TransfoLink { 
                            @CapellaID { eid = "e970b3de-59d1-4d6a-b5ea-223ad73e7794"; } 
                        }  
                    }  
                    dependency '1a8d0503-3ba1-4ab0-a77f-7fe941baaa86'
                        from 'Nose Landing Gear'::'Landing Gear Control and Indication Computer'::'eb7da3b1-ba85-4a01-b68f-2f17b0c9549e'
                        to  'Logical Architecture'::'Structure'::'UAV System'::'Drone'::'Vehicle Subsystems'::'Landing Gear Subsystem'::'4901f5e8-bffa-4bcf-8102-fe8b39ab5eb5' { 
                        @TransfoLink { 
                            @CapellaID { eid = "1a8d0503-3ba1-4ab0-a77f-7fe941baaa86"; } 
                        }  
                    }  
                    dependency 'a78170ce-d7a8-4ef4-afaf-3901c6e3d13d'
                        from 'Behavior Parent'::'d7343dea-ffd1-40c7-9aa8-3763cfc7f43b'
                        to  'Logical Architecture'::'Structure'::'UAV System'::'Drone'::'Vehicle Subsystems'::'Landing Gear Subsystem'::'Landing Gear'::'182b540e-e4c7-4dfc-a983-e96c7ce2e8cf' { 
                        @TransfoLink { 
                            @CapellaID { eid = "a78170ce-d7a8-4ef4-afaf-3901c6e3d13d"; } 
                        }  
                    }  
                    dependency 'b4325c95-437e-4cac-84c8-ef9ef7cf9085'
                        from 'Behavior Parent'::'d0f0f69b-337d-436e-bbcb-ffa9b124bf5b'
                        to  'Logical Architecture'::'Structure'::'UAV System'::'Drone'::'Vehicle Subsystems'::'6846da03-b57a-4110-bce3-e32f2698ffdb' { 
                        @TransfoLink { 
                            @CapellaID { eid = "b4325c95-437e-4cac-84c8-ef9ef7cf9085"; } 
                        }  
                    }  
                    dependency 'e7f242df-0c5d-4d21-9d9e-5004d3e6db66'
                        from 'Behavior Parent'::'fbe0c0b0-6bd7-466f-9c66-503dc3034368'
                        to  'Logical Architecture'::'Structure'::'UAV System'::'Drone'::'Vehicle Subsystems'::'9f9353c3-8032-41ef-b523-d1ceae0aaa73' { 
                        @TransfoLink { 
                            @CapellaID { eid = "e7f242df-0c5d-4d21-9d9e-5004d3e6db66"; } 
                        }  
                    }  
                    dependency 'af284189-7743-4544-a7f0-1c04553fd88c'
                        from 'Behavior Parent'::'5af834d3-aba6-444b-af4f-37795ca5c9ec'
                        to  'Logical Architecture'::'Structure'::'UAV System'::'Drone'::'Vehicle Subsystems'::'Landing Gear Subsystem'::'1d5b7b3f-fdd1-47aa-b8f7-0cace4d71687' { 
                        @TransfoLink { 
                            @CapellaID { eid = "af284189-7743-4544-a7f0-1c04553fd88c"; } 
                        }  
                    }  
                    dependency '3a7a8c2b-180b-4515-9c36-ff3dd87a8de0'
                        from 'Behavior Parent'::'d75405ec-e7b7-4a9d-86ed-f888d7af4602'
                        to  'Logical Architecture'::'Structure'::'UAV System'::'Drone'::'158621a6-4e6d-4bc3-bdf4-d44029f536ed' { 
                        @TransfoLink { 
                            @CapellaID { eid = "3a7a8c2b-180b-4515-9c36-ff3dd87a8de0"; } 
                        }  
                    }  
                    constraint 'f09109dd-6312-4f29-9918-4aba8afa50af' : CapellaConstraint { 
                        language "capella:linkedText" /*  */
                        @CapellaID { eid = "f09109dd-6312-4f29-9918-4aba8afa50af"; }
                        
                    } 
                    interface '9fa2ad25-5570-4ae7-a62c-d18729a78c4c' : ComponentExchange 
                        connect source ::> 'Behavior Parent'.'Fuel and Power System'.'FLIR'.'CP 1'
                        to  target ::> 'Behavior Parent'.'Fuel and Power System'.'ORS '.'CP 1' { 
                        @CapellaID { eid = "9fa2ad25-5570-4ae7-a62c-d18729a78c4c"; sid = "9fa2ad25-5570-4ae7-a62c-d18729a78c4c"; } 
                        attribute :>> kind = ComponentExchangeKind::FLOW; 
                        attribute :>> interfaceName = "FLIR-ORS"; 
                        attribute :>> isOriented = false; 
                        allocation '212c3477-bb2d-4919-adb6-260ec33e5983' : ComponentExchangeFunctionalExchangeAllocation
                            allocate functionalExchange ::> 'Physical Functions'::'Root Physical Function'.'b141216c-80c6-4f2e-b648-67772db4f2b3'
                            to componentExchange ::> '9fa2ad25-5570-4ae7-a62c-d18729a78c4c' { 
                            @CapellaID { eid = "212c3477-bb2d-4919-adb6-260ec33e5983"; sid = "212c3477-bb2d-4919-adb6-260ec33e5983"; } 
                             
                        }  
                        allocation '54cf5b59-0d5e-4141-acd8-03be7290ad1f' : ComponentExchangeFunctionalExchangeAllocation
                            allocate functionalExchange ::> 'Physical Functions'::'Root Physical Function'.'844fdd8e-cc79-44c9-abe8-9d977e6bf76d'
                            to componentExchange ::> '9fa2ad25-5570-4ae7-a62c-d18729a78c4c' { 
                            @CapellaID { eid = "54cf5b59-0d5e-4141-acd8-03be7290ad1f"; sid = "54cf5b59-0d5e-4141-acd8-03be7290ad1f"; } 
                             
                        }  
                        allocation '1bb82f00-2633-457c-a651-6daf899d4e12' : ComponentExchangeFunctionalExchangeAllocation
                            allocate functionalExchange ::> 'Physical Functions'::'Root Physical Function'.'24a38b00-19b1-48de-850e-4f435028df88'
                            to componentExchange ::> '9fa2ad25-5570-4ae7-a62c-d18729a78c4c' { 
                            @CapellaID { eid = "1bb82f00-2633-457c-a651-6daf899d4e12"; sid = "1bb82f00-2633-457c-a651-6daf899d4e12"; } 
                             
                        }  
                        allocation '59802bf7-e7a2-4ac8-9321-c53edbb5de74' : ComponentExchangeFunctionalExchangeAllocation
                            allocate functionalExchange ::> 'Physical Functions'::'Root Physical Function'.'3636a890-f283-4557-8fbf-87c7fbd83013'
                            to componentExchange ::> '9fa2ad25-5570-4ae7-a62c-d18729a78c4c' { 
                            @CapellaID { eid = "59802bf7-e7a2-4ac8-9321-c53edbb5de74"; sid = "59802bf7-e7a2-4ac8-9321-c53edbb5de74"; } 
                             
                        }  
                         
                        ref :>> ownedComponentExchangeFunctionalExchangeAllocations =  ('212c3477-bb2d-4919-adb6-260ec33e5983',
                        '54cf5b59-0d5e-4141-acd8-03be7290ad1f',
                        '1bb82f00-2633-457c-a651-6daf899d4e12',
                        '59802bf7-e7a2-4ac8-9321-c53edbb5de74'); 
                    }  
                    interface 'c04cefa7-1ebc-4db9-915f-effb64a09122' : ComponentExchange 
                        connect source ::> 'Behavior Parent'.'Fuel and Power System'.'ORS '.'CP 2'
                        to  target ::> 'Behavior Parent'.'ComLink'.'CP 3' { 
                        @CapellaID { eid = "c04cefa7-1ebc-4db9-915f-effb64a09122"; sid = "c04cefa7-1ebc-4db9-915f-effb64a09122"; } 
                        attribute :>> kind = ComponentExchangeKind::FLOW; 
                        attribute :>> interfaceName = "ORS to Com"; 
                        attribute :>> isOriented = false; 
                        allocation 'b9d57e01-a161-4d24-b6eb-1d0b2c38941c' : ComponentExchangeFunctionalExchangeAllocation
                            allocate functionalExchange ::> 'Physical Functions'::'Root Physical Function'.'85621e3d-1a84-45af-9235-c37b1a7aa9bd'
                            to componentExchange ::> 'c04cefa7-1ebc-4db9-915f-effb64a09122' { 
                            @CapellaID { eid = "b9d57e01-a161-4d24-b6eb-1d0b2c38941c"; sid = "b9d57e01-a161-4d24-b6eb-1d0b2c38941c"; } 
                             
                        }  
                        allocation '71223f6c-a369-44f3-b0b5-0d1452c480eb' : ComponentExchangeFunctionalExchangeAllocation
                            allocate functionalExchange ::> 'Physical Functions'::'Root Physical Function'.'12340e91-350b-40c8-8074-7d3584ea3bea'
                            to componentExchange ::> 'c04cefa7-1ebc-4db9-915f-effb64a09122' { 
                            @CapellaID { eid = "71223f6c-a369-44f3-b0b5-0d1452c480eb"; sid = "71223f6c-a369-44f3-b0b5-0d1452c480eb"; } 
                             
                        }  
                        allocation 'd5d132c5-9a38-494d-9325-072a6a11ff22' : ComponentExchangeFunctionalExchangeAllocation
                            allocate functionalExchange ::> 'Physical Functions'::'Root Physical Function'.'9a7c1e82-e3d2-4539-a01b-7569bbb0939f'
                            to componentExchange ::> 'c04cefa7-1ebc-4db9-915f-effb64a09122' { 
                            @CapellaID { eid = "d5d132c5-9a38-494d-9325-072a6a11ff22"; sid = "d5d132c5-9a38-494d-9325-072a6a11ff22"; } 
                             
                        }  
                         
                        ref :>> ownedComponentExchangeFunctionalExchangeAllocations =  ('b9d57e01-a161-4d24-b6eb-1d0b2c38941c',
                        '71223f6c-a369-44f3-b0b5-0d1452c480eb',
                        'd5d132c5-9a38-494d-9325-072a6a11ff22'); 
                    }  
                    interface '2e631237-b84b-4f27-b59b-42c6ec4fa809' : ComponentExchange 
                        connect source ::> 'Behavior Parent'.'Fuel and Power System'.'MC Comp'.'CP 1'
                        to  target ::> 'Behavior Parent'.'Fuel and Power System'.'ORS '.'CP 3' { 
                        @CapellaID { eid = "2e631237-b84b-4f27-b59b-42c6ec4fa809"; sid = "2e631237-b84b-4f27-b59b-42c6ec4fa809"; } 
                        attribute :>> kind = ComponentExchangeKind::FLOW; 
                        attribute :>> interfaceName = "MC- ORS"; 
                        attribute :>> isOriented = false; 
                        allocation '69726661-f625-49c6-bf62-c5dd6d013162' : ComponentExchangeFunctionalExchangeAllocation
                            allocate functionalExchange ::> 'Physical Functions'::'Root Physical Function'.'a9c8c5d1-a0aa-4fa8-9841-84cf667fb6e7'
                            to componentExchange ::> '2e631237-b84b-4f27-b59b-42c6ec4fa809' { 
                            @CapellaID { eid = "69726661-f625-49c6-bf62-c5dd6d013162"; sid = "69726661-f625-49c6-bf62-c5dd6d013162"; } 
                             
                        }  
                         
                        ref :>> ownedComponentExchangeFunctionalExchangeAllocations =  ('69726661-f625-49c6-bf62-c5dd6d013162'); 
                    }  
                    interface 'd2728b32-bce4-48f2-a74b-5ec6e1461bb3' : ComponentExchange 
                        connect source ::> 'Behavior Parent'.'NLG Door Sensor'.'CP 1'
                        to  target ::> 'Nose Landing Gear'.'Landing Gear Control and Indication Computer'.'Landing Gear Control and Indication Computer 1'.'CP 1' { 
                        @CapellaID { eid = "d2728b32-bce4-48f2-a74b-5ec6e1461bb3"; } 
                        attribute :>> kind = ComponentExchangeKind::FLOW; 
                        attribute :>> interfaceName = "NLG Door Sensor"; 
                        attribute :>> isOriented = false; 
                         
                    }  
                    interface 'e6b14846-d38a-4ba4-9b16-54c3ad760e76' : ComponentExchange 
                        connect source ::> 'Behavior Parent'.'Weight on Wheel Sensor 1'.'CP 1'
                        to  target ::> 'Nose Landing Gear'.'Landing Gear Control and Indication Computer'.'Landing Gear Control and Indication Computer 1'.'CP 2' { 
                        @CapellaID { eid = "e6b14846-d38a-4ba4-9b16-54c3ad760e76"; } 
                        attribute :>> kind = ComponentExchangeKind::FLOW; 
                        attribute :>> interfaceName = "Weight on Wheels 1"; 
                        attribute :>> isOriented = false; 
                        allocation 'b0ed85bc-1934-4364-8d36-a65935ab291b' : ComponentExchangeFunctionalExchangeAllocation
                            allocate functionalExchange ::> 'Physical Functions'::'Root Physical Function'.'1d0ef78d-bb0c-4929-ace7-8d0818fef271'
                            to componentExchange ::> 'e6b14846-d38a-4ba4-9b16-54c3ad760e76' { 
                            @CapellaID { eid = "b0ed85bc-1934-4364-8d36-a65935ab291b"; } 
                             
                        }  
                         
                        ref :>> ownedComponentExchangeFunctionalExchangeAllocations =  ('b0ed85bc-1934-4364-8d36-a65935ab291b'); 
                    }  
                    interface 'ab14a5c0-1ef4-450e-8b94-43c299476b40' : ComponentExchange 
                        connect source ::> 'Behavior Parent'.'Weight on Wheelp Sensor 2'.'CP 1'
                        to  target ::> 'Nose Landing Gear'.'Landing Gear Control and Indication Computer'.'Landing Gear Control and Indication Computer 1'.'CP 3' { 
                        @CapellaID { eid = "ab14a5c0-1ef4-450e-8b94-43c299476b40"; } 
                        attribute :>> kind = ComponentExchangeKind::FLOW; 
                        attribute :>> interfaceName = "Weight on Wheels 2"; 
                        attribute :>> isOriented = false; 
                        allocation '0932fc4f-a48e-44e7-b39d-8dd123e7eecc' : ComponentExchangeFunctionalExchangeAllocation
                            allocate functionalExchange ::> 'Physical Functions'::'Root Physical Function'.'004b4ee4-f50b-47d8-8ab8-684a3165d440'
                            to componentExchange ::> 'ab14a5c0-1ef4-450e-8b94-43c299476b40' { 
                            @CapellaID { eid = "0932fc4f-a48e-44e7-b39d-8dd123e7eecc"; } 
                             
                        }  
                         
                        ref :>> ownedComponentExchangeFunctionalExchangeAllocations =  ('0932fc4f-a48e-44e7-b39d-8dd123e7eecc'); 
                    }  
                    interface '15c2ccaf-6ff6-4697-915f-be6a9141728b' : ComponentExchange 
                        connect source ::> 'Behavior Parent'.'NLG Downlock Sensor 1'.'CP 1'
                        to  target ::> 'Nose Landing Gear'.'Landing Gear Control and Indication Computer'.'Landing Gear Control and Indication Computer 1'.'CP 4' { 
                        @CapellaID { eid = "15c2ccaf-6ff6-4697-915f-be6a9141728b"; } 
                        attribute :>> kind = ComponentExchangeKind::FLOW; 
                        attribute :>> interfaceName = "NLG Down Lock 1"; 
                        attribute :>> isOriented = false; 
                        allocation '377be2dc-8896-4a36-a501-695ca897a8ec' : ComponentExchangeFunctionalExchangeAllocation
                            allocate functionalExchange ::> 'Physical Functions'::'Root Physical Function'.'e464a43f-96dd-4638-84e3-50dcae0fc54c'
                            to componentExchange ::> '15c2ccaf-6ff6-4697-915f-be6a9141728b' { 
                            @CapellaID { eid = "377be2dc-8896-4a36-a501-695ca897a8ec"; } 
                             
                        }  
                         
                        ref :>> ownedComponentExchangeFunctionalExchangeAllocations =  ('377be2dc-8896-4a36-a501-695ca897a8ec'); 
                    }  
                    interface 'f82eef99-e3c8-4142-90ac-274d841119fc' : ComponentExchange 
                        connect source ::> 'Behavior Parent'.'NLG Uplock Sensor 2'.'CP 1'
                        to  target ::> 'Nose Landing Gear'.'Landing Gear Control and Indication Computer'.'Landing Gear Control and Indication Computer 1'.'CP 5' { 
                        @CapellaID { eid = "f82eef99-e3c8-4142-90ac-274d841119fc"; } 
                        attribute :>> kind = ComponentExchangeKind::FLOW; 
                        attribute :>> interfaceName = "NLG Uplock Position 2"; 
                        attribute :>> isOriented = false; 
                        allocation '91a6f4aa-639c-4b18-8b6b-cafcab5158af' : ComponentExchangeFunctionalExchangeAllocation
                            allocate functionalExchange ::> 'Physical Functions'::'Root Physical Function'.'800ff49e-cc73-4b71-9e22-27283841597f'
                            to componentExchange ::> 'f82eef99-e3c8-4142-90ac-274d841119fc' { 
                            @CapellaID { eid = "91a6f4aa-639c-4b18-8b6b-cafcab5158af"; } 
                             
                        }  
                         
                        ref :>> ownedComponentExchangeFunctionalExchangeAllocations =  ('91a6f4aa-639c-4b18-8b6b-cafcab5158af'); 
                    }  
                    interface '1b52869b-3804-4e5c-9c22-723937f25edc' : ComponentExchange 
                        connect source ::> 'Behavior Parent'.'NLG Downlock Sensor 2'.'CP 1'
                        to  target ::> 'Nose Landing Gear'.'Landing Gear Control and Indication Computer'.'Landing Gear Control and Indication Computer 1'.'CP 6' { 
                        @CapellaID { eid = "1b52869b-3804-4e5c-9c22-723937f25edc"; } 
                        attribute :>> kind = ComponentExchangeKind::FLOW; 
                        attribute :>> interfaceName = "NLG Downlock Sensor 2"; 
                        attribute :>> isOriented = false; 
                        allocation 'eb044881-17df-4186-8f56-eb36ddaf3989' : ComponentExchangeFunctionalExchangeAllocation
                            allocate functionalExchange ::> 'Physical Functions'::'Root Physical Function'.'2dc4a6c7-e5da-4c4b-b985-c50c84750e56'
                            to componentExchange ::> '1b52869b-3804-4e5c-9c22-723937f25edc' { 
                            @CapellaID { eid = "eb044881-17df-4186-8f56-eb36ddaf3989"; } 
                             
                        }  
                         
                        ref :>> ownedComponentExchangeFunctionalExchangeAllocations =  ('eb044881-17df-4186-8f56-eb36ddaf3989'); 
                    }  
                    interface 'bfacc4d7-c2ca-427d-9750-51e82d3234c7' : ComponentExchange 
                        connect source ::> 'Behavior Parent'.'NLG Uplock Sensor 1'.'CP 1'
                        to  target ::> 'Nose Landing Gear'.'Landing Gear Control and Indication Computer'.'Landing Gear Control and Indication Computer 1'.'CP 7' { 
                        @CapellaID { eid = "bfacc4d7-c2ca-427d-9750-51e82d3234c7"; } 
                        attribute :>> kind = ComponentExchangeKind::FLOW; 
                        attribute :>> interfaceName = "NLG Uplock Position 1"; 
                        attribute :>> isOriented = false; 
                        allocation 'dd6016dd-2b45-4788-b8d9-2081c3dbeced' : ComponentExchangeFunctionalExchangeAllocation
                            allocate functionalExchange ::> 'Physical Functions'::'Root Physical Function'.'0fe580e4-7e35-48b1-898c-3d7c1f790ec8'
                            to componentExchange ::> 'bfacc4d7-c2ca-427d-9750-51e82d3234c7' { 
                            @CapellaID { eid = "dd6016dd-2b45-4788-b8d9-2081c3dbeced"; } 
                             
                        }  
                         
                        ref :>> ownedComponentExchangeFunctionalExchangeAllocations =  ('dd6016dd-2b45-4788-b8d9-2081c3dbeced'); 
                    }  
                    interface '2627881e-1b24-458e-9423-13ab0016739a' : ComponentExchange 
                        connect source ::> 'Nose Landing Gear'.'Landing Gear Control and Indication Computer'.'Landing Gear Control and Indication Computer 1'.'CP 8'
                        to  target ::> 'Behavior Parent'.'NLG  Control Valve'.'CP 1' { 
                        @CapellaID { eid = "2627881e-1b24-458e-9423-13ab0016739a"; } 
                        attribute :>> kind = ComponentExchangeKind::FLOW; 
                        attribute :>> interfaceName = "NLG Command"; 
                        attribute :>> isOriented = false; 
                        allocation '4639c597-10e3-4965-adc9-1a354f2c35db' : ComponentExchangeFunctionalExchangeAllocation
                            allocate functionalExchange ::> 'Physical Functions'::'Root Physical Function'.'95abeb94-ee12-44d8-96f4-de9c3e32badf'
                            to componentExchange ::> '2627881e-1b24-458e-9423-13ab0016739a' { 
                            @CapellaID { eid = "4639c597-10e3-4965-adc9-1a354f2c35db"; } 
                             
                        }  
                         
                        ref :>> ownedComponentExchangeFunctionalExchangeAllocations =  ('4639c597-10e3-4965-adc9-1a354f2c35db'); 
                    }  
                    interface '62d8dd6a-ff5b-4df9-8c93-030c0c0a8617' : ComponentExchange 
                        connect source ::> 'Behavior Parent'.'NLG  Control Valve'.'CP 2'
                        to  target ::> 'Behavior Parent'.'NLG Wheel Steerin'.'CP 1' { 
                        @CapellaID { eid = "62d8dd6a-ff5b-4df9-8c93-030c0c0a8617"; } 
                        attribute :>> kind = ComponentExchangeKind::FLOW; 
                        attribute :>> interfaceName = "H-V to Act"; 
                        attribute :>> isOriented = false; 
                        allocation '8e54495e-5c32-47e1-b9a5-75caa2947a0e' : ComponentExchangeFunctionalExchangeAllocation
                            allocate functionalExchange ::> 'Physical Functions'::'Root Physical Function'.'Measure'.'Actuate NLG'.'0667513e-5428-4946-9a4d-299dbb7414f6'
                            to componentExchange ::> '62d8dd6a-ff5b-4df9-8c93-030c0c0a8617' { 
                            @CapellaID { eid = "8e54495e-5c32-47e1-b9a5-75caa2947a0e"; } 
                             
                        }  
                         
                        ref :>> ownedComponentExchangeFunctionalExchangeAllocations =  ('8e54495e-5c32-47e1-b9a5-75caa2947a0e'); 
                    }  
                    interface '64686ce1-271e-457e-890e-ef84e8b554f2' : ComponentExchange 
                        connect source ::> 'Behavior Parent'.'NLG Wheel Steerin'.'CP 2'
                        to  target ::> 'Behavior Parent'.'NLG Wheel'.'CP 1' { 
                        @CapellaID { eid = "64686ce1-271e-457e-890e-ef84e8b554f2"; } 
                        attribute :>> kind = ComponentExchangeKind::FLOW; 
                        attribute :>> interfaceName = "M- A to H"; 
                        attribute :>> isOriented = false; 
                        allocation '4db1ed48-bdc4-494b-8e3d-ea35221821cd' : ComponentExchangeFunctionalExchangeAllocation
                            allocate functionalExchange ::> 'Physical Functions'::'Root Physical Function'.'Measure'.'Actuate NLG'.'42d8592f-a0d0-48bd-9954-e64ff17fe414'
                            to componentExchange ::> '64686ce1-271e-457e-890e-ef84e8b554f2' { 
                            @CapellaID { eid = "4db1ed48-bdc4-494b-8e3d-ea35221821cd"; } 
                             
                        }  
                         
                        ref :>> ownedComponentExchangeFunctionalExchangeAllocations =  ('4db1ed48-bdc4-494b-8e3d-ea35221821cd'); 
                    }  
                    interface '095ee5c0-51ed-49ec-a9d8-889202d0cf1c' : ComponentExchange 
                        connect source ::> 'Behavior Parent'.'NLG Wheel'.'CP 2'
                        to  target ::> 'Behavior Parent'.'NLG Shock'.'CP 1' { 
                        @CapellaID { eid = "095ee5c0-51ed-49ec-a9d8-889202d0cf1c"; } 
                        attribute :>> kind = ComponentExchangeKind::FLOW; 
                        attribute :>> interfaceName = "M- H to A"; 
                        attribute :>> isOriented = false; 
                        allocation 'a92be31b-014f-4fcf-a7ed-b48d2f9a3cb5' : ComponentExchangeFunctionalExchangeAllocation
                            allocate functionalExchange ::> 'Physical Functions'::'Root Physical Function'.'16a8d621-e576-4365-bbb3-e65bea6bff08'
                            to componentExchange ::> '095ee5c0-51ed-49ec-a9d8-889202d0cf1c' { 
                            @CapellaID { eid = "a92be31b-014f-4fcf-a7ed-b48d2f9a3cb5"; } 
                             
                        }  
                         
                        ref :>> ownedComponentExchangeFunctionalExchangeAllocations =  ('a92be31b-014f-4fcf-a7ed-b48d2f9a3cb5'); 
                    }  
                    interface 'f1bb9dfc-09ec-4e9c-a2a1-2594f694cc06' : ComponentExchange 
                        connect source ::> 'Behavior Parent'.'NLG Wheel'.'CP 3'
                        to  target ::> 'Behavior Parent'.'NLG Struct Post'.'CP 1' { 
                        @CapellaID { eid = "f1bb9dfc-09ec-4e9c-a2a1-2594f694cc06"; } 
                        attribute :>> kind = ComponentExchangeKind::FLOW; 
                        attribute :>> interfaceName = "M-H to Post"; 
                        attribute :>> isOriented = false; 
                        allocation 'e9d394c5-a431-4878-8e72-cfef1523b86a' : ComponentExchangeFunctionalExchangeAllocation
                            allocate functionalExchange ::> 'Physical Functions'::'Root Physical Function'.'832de532-5107-4edb-a0e5-b610d918034f'
                            to componentExchange ::> 'f1bb9dfc-09ec-4e9c-a2a1-2594f694cc06' { 
                            @CapellaID { eid = "e9d394c5-a431-4878-8e72-cfef1523b86a"; } 
                             
                        }  
                         
                        ref :>> ownedComponentExchangeFunctionalExchangeAllocations =  ('e9d394c5-a431-4878-8e72-cfef1523b86a'); 
                    }  
                    interface 'bc6ac1ab-600c-4c5b-8e07-f645eb8296c7' : ComponentExchange 
                        connect source ::> 'Behavior Parent'.'NLG Struct Post'.'CP 2'
                        to  target ::> 'Behavior Parent'.'NLG Shock'.'CP 2' { 
                        @CapellaID { eid = "bc6ac1ab-600c-4c5b-8e07-f645eb8296c7"; } 
                        attribute :>> kind = ComponentExchangeKind::FLOW; 
                        attribute :>> interfaceName = "M- P to Shick"; 
                        attribute :>> isOriented = false; 
                        allocation 'da6c11a0-b48f-461a-b7c5-cbb2ae5b5672' : ComponentExchangeFunctionalExchangeAllocation
                            allocate functionalExchange ::> 'Physical Functions'::'Root Physical Function'.'Transmit NLG Forces'.'80b3ef0e-d505-453d-837d-9da01e94fde7'
                            to componentExchange ::> 'bc6ac1ab-600c-4c5b-8e07-f645eb8296c7' { 
                            @CapellaID { eid = "da6c11a0-b48f-461a-b7c5-cbb2ae5b5672"; } 
                             
                        }  
                         
                        ref :>> ownedComponentExchangeFunctionalExchangeAllocations =  ('da6c11a0-b48f-461a-b7c5-cbb2ae5b5672'); 
                    }  
                    interface '684fa9b7-b1b6-4bb2-be27-e6461fb9cbd8' : ComponentExchange 
                        connect source ::> 'Behavior Parent'.'NLG Door Actuator'.'CP 1'
                        to  target ::> 'Behavior Parent'.'Fuel and Power System'.'NLG Door'.'CP 1' { 
                        @CapellaID { eid = "684fa9b7-b1b6-4bb2-be27-e6461fb9cbd8"; } 
                        attribute :>> kind = ComponentExchangeKind::FLOW; 
                        attribute :>> interfaceName = "M-Door Act to NLG Door"; 
                        attribute :>> isOriented = false; 
                        allocation '7688af43-cff4-4afa-bf73-f04caf4f0df4' : ComponentExchangeFunctionalExchangeAllocation
                            allocate functionalExchange ::> 'Physical Functions'::'Root Physical Function'.'09f2e368-77ad-4836-b2f8-1a7c73051bec'
                            to componentExchange ::> '684fa9b7-b1b6-4bb2-be27-e6461fb9cbd8' { 
                            @CapellaID { eid = "7688af43-cff4-4afa-bf73-f04caf4f0df4"; } 
                             
                        }  
                         
                        ref :>> ownedComponentExchangeFunctionalExchangeAllocations =  ('7688af43-cff4-4afa-bf73-f04caf4f0df4'); 
                    }  
                    interface '9c229310-a429-4ba3-b497-3bc8ba12c21a' : ComponentExchange 
                        connect source ::> 'Behavior Parent'.'Airframe'.'CP 4'
                        to  target ::> 'Behavior Parent'.'Fuel and Power System'.'NLG Door'.'CP 2' { 
                        @CapellaID { eid = "9c229310-a429-4ba3-b497-3bc8ba12c21a"; } 
                        attribute :>> kind = ComponentExchangeKind::FLOW; 
                        attribute :>> interfaceName = "M-AF to NLG Door"; 
                        attribute :>> isOriented = false; 
                        allocation '1b04b028-cc5c-4fc0-aa01-77568e0a709b' : ComponentExchangeFunctionalExchangeAllocation
                            allocate functionalExchange ::> 'Physical Functions'::'Root Physical Function'.'5dc9b5f4-d936-4948-bbdd-b5e7c20a6468'
                            to componentExchange ::> '9c229310-a429-4ba3-b497-3bc8ba12c21a' { 
                            @CapellaID { eid = "1b04b028-cc5c-4fc0-aa01-77568e0a709b"; } 
                             
                        }  
                         
                        ref :>> ownedComponentExchangeFunctionalExchangeAllocations =  ('1b04b028-cc5c-4fc0-aa01-77568e0a709b'); 
                    }  
                    interface 'd8f1368f-1bf7-4788-b85a-7db80bc6814c' : ComponentExchange 
                        connect source ::> 'Behavior Parent'.'Extension Retraction Lever'.'CP 2'
                        to  target ::> 'Nose Landing Gear'.'Landing Gear Control and Indication Computer'.'Landing Gear Control and Indication Computer 1'.'CP 9' { 
                        @CapellaID { eid = "d8f1368f-1bf7-4788-b85a-7db80bc6814c"; } 
                        attribute :>> kind = ComponentExchangeKind::FLOW; 
                        attribute :>> interfaceName = "E-PI to LPG"; 
                        attribute :>> isOriented = false; 
                        allocation 'dfb9d658-eced-4fbb-918f-2f849168b058' : ComponentExchangeFunctionalExchangeAllocation
                            allocate functionalExchange ::> 'Physical Functions'::'Root Physical Function'.'4c3fd424-a65e-46d2-8687-718dfacf40e2'
                            to componentExchange ::> 'd8f1368f-1bf7-4788-b85a-7db80bc6814c' { 
                            @CapellaID { eid = "dfb9d658-eced-4fbb-918f-2f849168b058"; } 
                             
                        }  
                         
                        ref :>> ownedComponentExchangeFunctionalExchangeAllocations =  ('dfb9d658-eced-4fbb-918f-2f849168b058'); 
                    }  
                    interface '52cec165-5171-4290-b050-7c0c61e0004d' : ComponentExchange 
                        connect source ::> 'Behavior Parent'.'Fuel and Power System'.'Dump Control'.'CP 3'
                        to  target ::> 'Behavior Parent'.'NLG Doors Dump Valve'.'CP 1' { 
                        @CapellaID { eid = "52cec165-5171-4290-b050-7c0c61e0004d"; } 
                        attribute :>> kind = ComponentExchangeKind::FLOW; 
                        attribute :>> interfaceName = "M- NLG Door Dump"; 
                        attribute :>> isOriented = false; 
                        allocation '91afa091-1787-48fb-bd0c-98dc41f46af1' : ComponentExchangeFunctionalExchangeAllocation
                            allocate functionalExchange ::> 'Physical Functions'::'Root Physical Function'.'8a9a972f-7c53-4fde-8364-eca5e86c5fe5'
                            to componentExchange ::> '52cec165-5171-4290-b050-7c0c61e0004d' { 
                            @CapellaID { eid = "91afa091-1787-48fb-bd0c-98dc41f46af1"; } 
                             
                        }  
                         
                        ref :>> ownedComponentExchangeFunctionalExchangeAllocations =  ('91afa091-1787-48fb-bd0c-98dc41f46af1'); 
                    }  
                    interface '7b11072b-491a-4690-bad8-f845679271a2' : ComponentExchange 
                        connect source ::> 'Behavior Parent'.'Fuel and Power System'.'Dump Control'.'CP 4'
                        to  target ::> 'Behavior Parent'.'NLG Dump Valve'.'CP 1' { 
                        @CapellaID { eid = "7b11072b-491a-4690-bad8-f845679271a2"; } 
                        attribute :>> kind = ComponentExchangeKind::FLOW; 
                        attribute :>> interfaceName = "M-NLG Dump"; 
                        attribute :>> isOriented = false; 
                        allocation 'd3687cb6-15f7-4cfd-999c-e741beb27c03' : ComponentExchangeFunctionalExchangeAllocation
                            allocate functionalExchange ::> 'Physical Functions'::'Root Physical Function'.'ecfbd774-e962-4196-a4d1-d8026752c9e5'
                            to componentExchange ::> '7b11072b-491a-4690-bad8-f845679271a2' { 
                            @CapellaID { eid = "d3687cb6-15f7-4cfd-999c-e741beb27c03"; } 
                             
                        }  
                         
                        ref :>> ownedComponentExchangeFunctionalExchangeAllocations =  ('d3687cb6-15f7-4cfd-999c-e741beb27c03'); 
                    }  
                    interface '35a702e1-ac98-4180-85ff-e18405633f49' : ComponentExchange 
                        connect source ::> 'Behavior Parent'.'NLG Doors Selector Valve'.'CP 2'
                        to  target ::> 'Behavior Parent'.'NLG Door Actuator'.'CP 2' { 
                        @CapellaID { eid = "35a702e1-ac98-4180-85ff-e18405633f49"; } 
                        attribute :>> kind = ComponentExchangeKind::FLOW; 
                        attribute :>> interfaceName = "H-MLG Door DV"; 
                        attribute :>> isOriented = false; 
                        allocation '1cc87cdf-78ae-4fa3-9763-e42b16a9ce26' : ComponentExchangeFunctionalExchangeAllocation
                            allocate functionalExchange ::> 'Physical Functions'::'Root Physical Function'.'3fcc6e64-59a4-4362-8a29-7ef25d1d33ef'
                            to componentExchange ::> '35a702e1-ac98-4180-85ff-e18405633f49' { 
                            @CapellaID { eid = "1cc87cdf-78ae-4fa3-9763-e42b16a9ce26"; } 
                             
                        }  
                         
                        ref :>> ownedComponentExchangeFunctionalExchangeAllocations =  ('1cc87cdf-78ae-4fa3-9763-e42b16a9ce26'); 
                    }  
                    interface '16a559d3-a34a-4e83-a52b-4c5d265ce1ef' : ComponentExchange 
                        connect source ::> 'Behavior Parent'.'NLG Doors Dump Valve'.'CP 2'
                        to  target ::> 'Behavior Parent'.'NLG Doors Selector Valve'.'CP 3' { 
                        @CapellaID { eid = "16a559d3-a34a-4e83-a52b-4c5d265ce1ef"; } 
                        attribute :>> kind = ComponentExchangeKind::FLOW; 
                        attribute :>> interfaceName = "Dump Valve to Selector Valve Pressure"; 
                        attribute :>> isOriented = false; 
                        allocation 'd1fa947b-c86f-4afe-8e96-8307df129472' : ComponentExchangeFunctionalExchangeAllocation
                            allocate functionalExchange ::> 'Physical Functions'::'Root Physical Function'.'dd24e1c6-d1aa-4685-ace8-724913363a1a'
                            to componentExchange ::> '16a559d3-a34a-4e83-a52b-4c5d265ce1ef' { 
                            @CapellaID { eid = "d1fa947b-c86f-4afe-8e96-8307df129472"; } 
                             
                        }  
                         
                        ref :>> ownedComponentExchangeFunctionalExchangeAllocations =  ('d1fa947b-c86f-4afe-8e96-8307df129472'); 
                    }  
                    interface 'cbd135f0-e619-4859-ac05-95ec6622490e' : ComponentExchange 
                        connect source ::> 'Behavior Parent'.'NLG Doors Dump Valve'.'CP 3'
                        to  target ::> 'Behavior Parent'.'Fuel and Power System'.'H R'.'CP 1' { 
                        @CapellaID { eid = "cbd135f0-e619-4859-ac05-95ec6622490e"; } 
                        attribute :>> kind = ComponentExchangeKind::FLOW; 
                        attribute :>> interfaceName = "Dump Valve to Reservoir Return"; 
                        attribute :>> isOriented = false; 
                        allocation 'b69fcd5d-ef57-45bf-a4e8-18f9a2ec60d4' : ComponentExchangeFunctionalExchangeAllocation
                            allocate functionalExchange ::> 'Physical Functions'::'Root Physical Function'.'c4b6b216-e81c-4e1b-b059-195564f4e397'
                            to componentExchange ::> 'cbd135f0-e619-4859-ac05-95ec6622490e' { 
                            @CapellaID { eid = "b69fcd5d-ef57-45bf-a4e8-18f9a2ec60d4"; } 
                             
                        }  
                         
                        ref :>> ownedComponentExchangeFunctionalExchangeAllocations =  ('b69fcd5d-ef57-45bf-a4e8-18f9a2ec60d4'); 
                    }  
                    interface '60b22a4a-8789-4f62-8476-a67077e8dd97' : ComponentExchange 
                        connect source ::> 'Behavior Parent'.'Airframe'.'CP 5'
                        to  target ::> 'Behavior Parent'.'NLG Struct Post'.'CP 3' { 
                        @CapellaID { eid = "60b22a4a-8789-4f62-8476-a67077e8dd97"; } 
                        attribute :>> kind = ComponentExchangeKind::FLOW; 
                        attribute :>> interfaceName = "Airframe to Strut Post Interface"; 
                        attribute :>> isOriented = false; 
                        allocation '58180733-9c92-4914-b94a-9302585dfbcb' : ComponentExchangeFunctionalExchangeAllocation
                            allocate functionalExchange ::> 'Physical Functions'::'Root Physical Function'.'e9d0cadd-34a1-4f2d-8be6-334fd4af0052'
                            to componentExchange ::> '60b22a4a-8789-4f62-8476-a67077e8dd97' { 
                            @CapellaID { eid = "58180733-9c92-4914-b94a-9302585dfbcb"; } 
                             
                        }  
                        allocation 'cf976f80-34d3-4322-bcd1-5f4f6be299cf' : ComponentExchangeFunctionalExchangeAllocation
                            allocate functionalExchange ::> 'Physical Functions'::'Root Physical Function'.'e8026413-6760-47f1-bdb5-eff8b873c988'
                            to componentExchange ::> '60b22a4a-8789-4f62-8476-a67077e8dd97' { 
                            @CapellaID { eid = "cf976f80-34d3-4322-bcd1-5f4f6be299cf"; } 
                             
                        }  
                         
                        ref :>> ownedComponentExchangeFunctionalExchangeAllocations =  ('58180733-9c92-4914-b94a-9302585dfbcb',
                        'cf976f80-34d3-4322-bcd1-5f4f6be299cf'); 
                    }  
                    part 'f85f4b9b-ae97-4bae-9d0b-275e3db4839f' : CPart :> 'Aerial Platform'  { 
                        @CapellaID { eid = "f85f4b9b-ae97-4bae-9d0b-275e3db4839f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part '4fdae0ea-a728-48d5-9964-7c80ccc8b707' : CPart :> 'Ground System'  { 
                        @CapellaID { eid = "4fdae0ea-a728-48d5-9964-7c80ccc8b707"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part 'c72eea44-f9bc-446d-a152-bdac894bf8d0' : CPart :> 'Up Link'  { 
                        @CapellaID { eid = "c72eea44-f9bc-446d-a152-bdac894bf8d0"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part 'f6891f84-9a83-4a87-a6e8-e5013e5e72d5' : CPart :> 'Satellite'  { 
                        @CapellaID { eid = "f6891f84-9a83-4a87-a6e8-e5013e5e72d5"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part '287fe307-b239-48d5-a4cd-246082cfb218' : CPart :> 'Avionics'  { 
                        @CapellaID { eid = "287fe307-b239-48d5-a4cd-246082cfb218"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part 'c4bbe862-0d17-4f59-a2ac-fe97774970dd' : CPart :> 'Vehicle Subsystems'  { 
                        @CapellaID { eid = "c4bbe862-0d17-4f59-a2ac-fe97774970dd"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part 'e98c0a34-a0c0-43dd-95b9-50ae9a614aec' : CPart :> 'Propulsion'  { 
                        @CapellaID { eid = "e98c0a34-a0c0-43dd-95b9-50ae9a614aec"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part 'bf10bdb8-326a-4808-b81c-7e4b54c31b41' : CPart :> 'Fuselage'  { 
                        @CapellaID { eid = "bf10bdb8-326a-4808-b81c-7e4b54c31b41"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part 'a5e44475-c61f-4d8f-b106-8b7d6cfc19f3' : CPart :> 'Empennage'  { 
                        @CapellaID { eid = "a5e44475-c61f-4d8f-b106-8b7d6cfc19f3"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part 'd8f665b8-1d64-408a-91bd-c84377c32d14' : CPart :> 'S Wing'  { 
                        @CapellaID { eid = "d8f665b8-1d64-408a-91bd-c84377c32d14"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part '599e2033-5848-4e2a-b601-490d3cba582a' : CPart :> 'P Wing'  { 
                        @CapellaID { eid = "599e2033-5848-4e2a-b601-490d3cba582a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part '958779f0-af8e-47c2-bbce-87d0126b7d11' : CPart :> 'Drone'  { 
                        @CapellaID { eid = "958779f0-af8e-47c2-bbce-87d0126b7d11"; sid = "d2b60dd0-657b-41ef-88fa-62ad2ed1e88a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part 'fddac96a-1e88-4195-8d04-a06666ae892e' : CPart :> 'FLIR'  { 
                        @CapellaID { eid = "fddac96a-1e88-4195-8d04-a06666ae892e"; sid = "fddac96a-1e88-4195-8d04-a06666ae892e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation '872362fe-5677-4a58-997c-dd08692e3a5f' : PartDeploymentLink
                            allocate deployedElement ::> 'Behavior Parent'.'Fuel and Power System'.'0bfea9de-7cea-42ed-9ad2-d930ca24d9d4'
                            to location ::> 'Nose Landing Gear Library'::'Nose Landing Gear'::'Physical Architecture'::'Structure'::'Physical System'.'fddac96a-1e88-4195-8d04-a06666ae892e' { 
                            @CapellaID { eid = "872362fe-5677-4a58-997c-dd08692e3a5f"; sid = "872362fe-5677-4a58-997c-dd08692e3a5f"; } 
                             
                        }  
                        ref :>> ownedDeploymentLinks =  ('872362fe-5677-4a58-997c-dd08692e3a5f'); 
                         
                    }  
                    part 'e6162a6a-d2e6-43b4-96b3-f38bf8a08d78' : CPart :> 'Object Recognition System'  { 
                        @CapellaID { eid = "e6162a6a-d2e6-43b4-96b3-f38bf8a08d78"; sid = "e6162a6a-d2e6-43b4-96b3-f38bf8a08d78"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation '3c50bfb5-d31b-49e4-97c9-9fc4e9979344' : PartDeploymentLink
                            allocate deployedElement ::> 'Behavior Parent'.'Fuel and Power System'.'2d01be52-4237-4b3f-b61c-4443ad4cb71d'
                            to location ::> 'Nose Landing Gear Library'::'Nose Landing Gear'::'Physical Architecture'::'Structure'::'Physical System'.'e6162a6a-d2e6-43b4-96b3-f38bf8a08d78' { 
                            @CapellaID { eid = "3c50bfb5-d31b-49e4-97c9-9fc4e9979344"; sid = "3c50bfb5-d31b-49e4-97c9-9fc4e9979344"; } 
                             
                        }  
                        ref :>> ownedDeploymentLinks =  ('3c50bfb5-d31b-49e4-97c9-9fc4e9979344'); 
                         
                    }  
                    part '382ea1a4-c996-48cb-be10-7fe5617a5c5e' : CPart :> 'COM LInk'  { 
                        @CapellaID { eid = "382ea1a4-c996-48cb-be10-7fe5617a5c5e"; sid = "382ea1a4-c996-48cb-be10-7fe5617a5c5e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation 'dca5b116-d467-4229-88be-bf35d8d5d788' : PartDeploymentLink
                            allocate deployedElement ::> 'Behavior Parent'.'8ceab8e5-ef83-4b89-b7a6-0926940807dd'
                            to location ::> 'Nose Landing Gear Library'::'Nose Landing Gear'::'Physical Architecture'::'Structure'::'Physical System'.'382ea1a4-c996-48cb-be10-7fe5617a5c5e' { 
                            @CapellaID { eid = "dca5b116-d467-4229-88be-bf35d8d5d788"; sid = "dca5b116-d467-4229-88be-bf35d8d5d788"; } 
                             
                        }  
                        ref :>> ownedDeploymentLinks =  ('dca5b116-d467-4229-88be-bf35d8d5d788'); 
                         
                    }  
                    part '8842e675-57dd-48cc-884e-e71376acbd5e' : CPart :> 'Mission Computer'  { 
                        @CapellaID { eid = "8842e675-57dd-48cc-884e-e71376acbd5e"; sid = "8842e675-57dd-48cc-884e-e71376acbd5e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation 'f82d41d4-94ce-4a9e-a7d3-af89fc1515b9' : PartDeploymentLink
                            allocate deployedElement ::> 'Behavior Parent'.'Fuel and Power System'.'c0203ad1-a911-42f8-bd95-83b39df5bfac'
                            to location ::> 'Nose Landing Gear Library'::'Nose Landing Gear'::'Physical Architecture'::'Structure'::'Physical System'.'8842e675-57dd-48cc-884e-e71376acbd5e' { 
                            @CapellaID { eid = "f82d41d4-94ce-4a9e-a7d3-af89fc1515b9"; sid = "f82d41d4-94ce-4a9e-a7d3-af89fc1515b9"; } 
                             
                        }  
                        ref :>> ownedDeploymentLinks =  ('f82d41d4-94ce-4a9e-a7d3-af89fc1515b9'); 
                         
                    }  
                    part 'c991b264-649e-4d80-bfa3-aea982e23488' : CPart :> 'Braking System Control Unit (BSCU)'  { 
                        @CapellaID { eid = "c991b264-649e-4d80-bfa3-aea982e23488"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation '648b419d-900b-40ee-acb6-8079c2fdab7a' : PartDeploymentLink
                            allocate deployedElement ::> 'Behavior Parent'.'Fuel and Power System'.'43702048-23d3-441a-adfe-e2872730f75b'
                            to location ::> 'Nose Landing Gear Library'::'Nose Landing Gear'::'Physical Architecture'::'Structure'::'Physical System'.'c991b264-649e-4d80-bfa3-aea982e23488' { 
                            @CapellaID { eid = "648b419d-900b-40ee-acb6-8079c2fdab7a"; } 
                             
                        }  
                        allocation '8405b8c4-73c3-4867-b770-16e91d08d04d' : PartDeploymentLink
                            allocate deployedElement ::> 'Behavior Parent'.'Fuel and Power System'.'a1468a51-64d3-45ed-b71f-2a6b00c95928'
                            to location ::> 'Nose Landing Gear Library'::'Nose Landing Gear'::'Physical Architecture'::'Structure'::'Physical System'.'c991b264-649e-4d80-bfa3-aea982e23488' { 
                            @CapellaID { eid = "8405b8c4-73c3-4867-b770-16e91d08d04d"; } 
                             
                        }  
                        ref :>> ownedDeploymentLinks =  ('648b419d-900b-40ee-acb6-8079c2fdab7a',
                        '8405b8c4-73c3-4867-b770-16e91d08d04d'); 
                         
                    }  
                    part '2b2ee774-8482-44b9-88ec-5477fe966d40' : CPart :> 'Hydralic Reservoir'  { 
                        @CapellaID { eid = "2b2ee774-8482-44b9-88ec-5477fe966d40"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation '92b078dd-9680-4364-879b-da8c54655b41' : PartDeploymentLink
                            allocate deployedElement ::> 'Behavior Parent'.'27e6a2fc-6333-416b-8605-0293d9ff16a7'
                            to location ::> 'Nose Landing Gear Library'::'Nose Landing Gear'::'Physical Architecture'::'Structure'::'Physical System'.'2b2ee774-8482-44b9-88ec-5477fe966d40' { 
                            @CapellaID { eid = "92b078dd-9680-4364-879b-da8c54655b41"; } 
                             
                        }  
                        ref :>> ownedDeploymentLinks =  ('92b078dd-9680-4364-879b-da8c54655b41'); 
                         
                    }  
                    part '0955b18d-3e19-48e4-b0c4-164d61bf9ec4' : CPart :> 'Avionics Control'  { 
                        @CapellaID { eid = "0955b18d-3e19-48e4-b0c4-164d61bf9ec4"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation 'f5850d2d-929d-4ac1-baec-4dd0c8782cb8' : PartDeploymentLink
                            allocate deployedElement ::> 'Behavior Parent'.'49713b75-2374-424c-8288-3a62dc79a3f5'
                            to location ::> 'Nose Landing Gear Library'::'Nose Landing Gear'::'Physical Architecture'::'Structure'::'Physical System'.'0955b18d-3e19-48e4-b0c4-164d61bf9ec4' { 
                            @CapellaID { eid = "f5850d2d-929d-4ac1-baec-4dd0c8782cb8"; } 
                             
                        }  
                        ref :>> ownedDeploymentLinks =  ('f5850d2d-929d-4ac1-baec-4dd0c8782cb8'); 
                         
                    }  
                    part '0c72c47c-f64f-428e-b562-aefcfa05e29d' : CPart :> 'Braking Hydralulic Subsystem'  { 
                        @CapellaID { eid = "0c72c47c-f64f-428e-b562-aefcfa05e29d"; sid = "0c72c47c-f64f-428e-b562-aefcfa05e29d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part 'e5f7dd47-4e22-4b72-9573-3ecaafeb741b' : CPart :> 'Hydraulic '  { 
                        @CapellaID { eid = "e5f7dd47-4e22-4b72-9573-3ecaafeb741b"; sid = "e5f7dd47-4e22-4b72-9573-3ecaafeb741b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation '5d926013-fb2e-4db2-9b3b-a23562309cd7' : PartDeploymentLink
                            allocate deployedElement ::> 'Behavior Parent'.'2ab53a75-5e83-49ac-a1ec-aaac190cc8c0'
                            to location ::> 'Nose Landing Gear Library'::'Nose Landing Gear'::'Physical Architecture'::'Structure'::'Physical System'.'e5f7dd47-4e22-4b72-9573-3ecaafeb741b' { 
                            @CapellaID { eid = "5d926013-fb2e-4db2-9b3b-a23562309cd7"; } 
                             
                        }  
                        ref :>> ownedDeploymentLinks =  ('5d926013-fb2e-4db2-9b3b-a23562309cd7'); 
                         
                    }  
                    part 'f5d9391f-f598-400d-b998-df1be650c793' : CPart :> 'Airframe'  { 
                        @CapellaID { eid = "f5d9391f-f598-400d-b998-df1be650c793"; sid = "f5d9391f-f598-400d-b998-df1be650c793"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation 'f080726f-d7df-4365-b9ba-92a2e86c5e5b' : PartDeploymentLink
                            allocate deployedElement ::> 'Behavior Parent'.'d75405ec-e7b7-4a9d-86ed-f888d7af4602'
                            to location ::> 'Nose Landing Gear Library'::'Nose Landing Gear'::'Physical Architecture'::'Structure'::'Physical System'.'f5d9391f-f598-400d-b998-df1be650c793' { 
                            @CapellaID { eid = "f080726f-d7df-4365-b9ba-92a2e86c5e5b"; } 
                             
                        }  
                        ref :>> ownedDeploymentLinks =  ('f080726f-d7df-4365-b9ba-92a2e86c5e5b'); 
                         
                    }  
                    part '60ac8845-3b3b-442c-bb30-54d2628c6c80' : CPart :> 'Data Bus 1'  { 
                        @CapellaID { eid = "60ac8845-3b3b-442c-bb30-54d2628c6c80"; sid = "60ac8845-3b3b-442c-bb30-54d2628c6c80"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part '51ee384c-1f3c-47fe-8861-ea76e8c00398' : CPart :> 'Bus 1'  { 
                        @CapellaID { eid = "51ee384c-1f3c-47fe-8861-ea76e8c00398"; sid = "51ee384c-1f3c-47fe-8861-ea76e8c00398"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part '9a899522-f556-41cf-b0e6-4106e26df4f5' : CPart :> 'LGL Harness'  { 
                        @CapellaID { eid = "9a899522-f556-41cf-b0e6-4106e26df4f5"; sid = "9a899522-f556-41cf-b0e6-4106e26df4f5"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part '96cf6c71-2e21-4b57-9429-edbcd812318a' : CPart :> 'Nose Landing Gear'  { 
                        @CapellaID { eid = "96cf6c71-2e21-4b57-9429-edbcd812318a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part '93ac104d-f632-416d-928a-80b588c96b9d' : CPart :> 'Port Com Bus'  { 
                        @CapellaID { eid = "93ac104d-f632-416d-928a-80b588c96b9d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    part '79f58c1c-c76c-4673-8bee-23b2987c69b8' : CPart :> 'NLG Door'  { 
                        @CapellaID { eid = "79f58c1c-c76c-4673-8bee-23b2987c69b8"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation '7621624c-54ba-438c-b2c3-47ca8f281851' : PartDeploymentLink
                            allocate deployedElement ::> 'Behavior Parent'.'Fuel and Power System'.'37e28ec9-9e30-4740-978f-68fdcd7461d0'
                            to location ::> 'Nose Landing Gear Library'::'Nose Landing Gear'::'Physical Architecture'::'Structure'::'Physical System'.'79f58c1c-c76c-4673-8bee-23b2987c69b8' { 
                            @CapellaID { eid = "7621624c-54ba-438c-b2c3-47ca8f281851"; } 
                             
                        }  
                        ref :>> ownedDeploymentLinks =  ('7621624c-54ba-438c-b2c3-47ca8f281851'); 
                         
                    }  
                    part 'd3526301-ab15-406d-b149-ab4088d28cb7' : CPart :> 'H3'  { 
                        @CapellaID { eid = "d3526301-ab15-406d-b149-ab4088d28cb7"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation 'ae1d4474-3548-42f1-ba11-2c838c5b4ca5' : PartDeploymentLink
                            allocate deployedElement ::> 'Behavior Parent'.'d0f0f69b-337d-436e-bbcb-ffa9b124bf5b'
                            to location ::> 'Nose Landing Gear Library'::'Nose Landing Gear'::'Physical Architecture'::'Structure'::'Physical System'.'d3526301-ab15-406d-b149-ab4088d28cb7' { 
                            @CapellaID { eid = "ae1d4474-3548-42f1-ba11-2c838c5b4ca5"; } 
                             
                        }  
                        ref :>> ownedDeploymentLinks =  ('ae1d4474-3548-42f1-ba11-2c838c5b4ca5'); 
                         
                    }  
                    part '8e111027-0f23-4012-ad7f-3507d2dd7124' : CPart :> 'H2'  { 
                        @CapellaID { eid = "8e111027-0f23-4012-ad7f-3507d2dd7124"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation '611e0f17-dbec-4a25-bbf2-843d0acc9dc2' : PartDeploymentLink
                            allocate deployedElement ::> 'Behavior Parent'.'Fuel and Power System'.'c7478463-a226-4394-98f2-4189b801342c'
                            to location ::> 'Nose Landing Gear Library'::'Nose Landing Gear'::'Physical Architecture'::'Structure'::'Physical System'.'8e111027-0f23-4012-ad7f-3507d2dd7124' { 
                            @CapellaID { eid = "611e0f17-dbec-4a25-bbf2-843d0acc9dc2"; } 
                             
                        }  
                        ref :>> ownedDeploymentLinks =  ('611e0f17-dbec-4a25-bbf2-843d0acc9dc2'); 
                         
                    }  
                    part 'c0daad27-fa54-4df5-9279-55c33a4827f8' : CPart :> 'H Reservoir'  { 
                        @CapellaID { eid = "c0daad27-fa54-4df5-9279-55c33a4827f8"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation 'd2f29bd4-fc3c-45ea-9e0e-2f712ee9d48e' : PartDeploymentLink
                            allocate deployedElement ::> 'Behavior Parent'.'Fuel and Power System'.'51742133-7795-453d-86db-1ac786344f3a'
                            to location ::> 'Nose Landing Gear Library'::'Nose Landing Gear'::'Physical Architecture'::'Structure'::'Physical System'.'c0daad27-fa54-4df5-9279-55c33a4827f8' { 
                            @CapellaID { eid = "d2f29bd4-fc3c-45ea-9e0e-2f712ee9d48e"; } 
                             
                        }  
                        ref :>> ownedDeploymentLinks =  ('d2f29bd4-fc3c-45ea-9e0e-2f712ee9d48e'); 
                         
                    }  
                    part '40507597-7731-4350-9066-8f3cc247bbf8' : CPart :> 'Pilot Interface'  { 
                        @CapellaID { eid = "40507597-7731-4350-9066-8f3cc247bbf8"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation '334d712d-fff8-463c-bc83-45963784cda7' : PartDeploymentLink
                            allocate deployedElement ::> 'Behavior Parent'.'5af834d3-aba6-444b-af4f-37795ca5c9ec'
                            to location ::> 'Nose Landing Gear Library'::'Nose Landing Gear'::'Physical Architecture'::'Structure'::'Physical System'.'40507597-7731-4350-9066-8f3cc247bbf8' { 
                            @CapellaID { eid = "334d712d-fff8-463c-bc83-45963784cda7"; } 
                             
                        }  
                        allocation '6354d7f3-3157-4004-a552-f09e59b5c7d8' : PartDeploymentLink
                            allocate deployedElement ::> 'Behavior Parent'.'Fuel and Power System'.'b4eca515-0a19-4c0e-968b-1a7ffd9ae240'
                            to location ::> 'Nose Landing Gear Library'::'Nose Landing Gear'::'Physical Architecture'::'Structure'::'Physical System'.'40507597-7731-4350-9066-8f3cc247bbf8' { 
                            @CapellaID { eid = "6354d7f3-3157-4004-a552-f09e59b5c7d8"; } 
                             
                        }  
                        ref :>> ownedDeploymentLinks =  ('334d712d-fff8-463c-bc83-45963784cda7',
                        '6354d7f3-3157-4004-a552-f09e59b5c7d8'); 
                         
                    }  
                    part '17c92499-60de-44be-b621-f2dcf6258391' : CPart :> 'NLG Dump Valve'  { 
                        @CapellaID { eid = "17c92499-60de-44be-b621-f2dcf6258391"; sid = "17c92499-60de-44be-b621-f2dcf6258391"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation '0cae370e-0a19-4b43-937d-3f70d00dc694' : PartDeploymentLink
                            allocate deployedElement ::> 'Behavior Parent'.'26ce5afc-104f-4b53-8dcd-4e427b97ab8a'
                            to location ::> 'Nose Landing Gear Library'::'Nose Landing Gear'::'Physical Architecture'::'Structure'::'Physical System'.'17c92499-60de-44be-b621-f2dcf6258391' { 
                            @CapellaID { eid = "0cae370e-0a19-4b43-937d-3f70d00dc694"; } 
                             
                        }  
                        ref :>> ownedDeploymentLinks =  ('0cae370e-0a19-4b43-937d-3f70d00dc694'); 
                         
                    }  
                    part '99b977de-7dfe-47ab-9ebd-8a734d6b9d10' : CPart :> 'ion '  { 
                        @CapellaID { eid = "99b977de-7dfe-47ab-9ebd-8a734d6b9d10"; sid = "99b977de-7dfe-47ab-9ebd-8a734d6b9d10"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        allocation 'bfb494d5-e315-4afe-9d47-9a0646c54fd4' : PartDeploymentLink
                            allocate deployedElement ::> 'Behavior Parent'.'da1e3920-5a9a-463a-add6-97969bbe19d1'
                            to location ::> 'Nose Landing Gear Library'::'Nose Landing Gear'::'Physical Architecture'::'Structure'::'Physical System'.'99b977de-7dfe-47ab-9ebd-8a734d6b9d10' { 
                            @CapellaID { eid = "bfb494d5-e315-4afe-9d47-9a0646c54fd4"; } 
                             
                        }  
                        ref :>> ownedDeploymentLinks =  ('bfb494d5-e315-4afe-9d47-9a0646c54fd4'); 
                         
                    }  
                    part '7fdec3b1-4da8-4e29-8390-9f05b110f5dc' : CPart :> 'Behavior Parent'  { 
                        @CapellaID { eid = "7fdec3b1-4da8-4e29-8390-9f05b110f5dc"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    interface 'e6e7ba72-9242-40ce-bde0-d8993ec88345' : PhysicalLink 
                        connect sourcePhysicalPort ::> 'Avionics'.'PP 7'
                        to targetPhysicalPort ::> 'Fuselage'.'PP 7' {
                        @CapellaID { eid = "e6e7ba72-9242-40ce-bde0-d8993ec88345"; } 
                        attribute :>> interfaceName = "PL 4"; 
                         
                    }  
                    interface 'a385361e-0e4b-462b-824c-f8368492c26a' : PhysicalLink 
                        connect sourcePhysicalPort ::> 'Vehicle Subsystems'.'PP 9'
                        to targetPhysicalPort ::> 'Fuselage'.'PP 6' {
                        @CapellaID { eid = "a385361e-0e4b-462b-824c-f8368492c26a"; } 
                        attribute :>> interfaceName = "PL 3"; 
                         
                    }  
                    interface '5e36f45b-e114-47af-a75d-bf480e24c06d' : PhysicalLink 
                        connect sourcePhysicalPort ::> 'Propulsion'.'PP 1'
                        to targetPhysicalPort ::> 'Fuselage'.'PP 1' {
                        @CapellaID { eid = "5e36f45b-e114-47af-a75d-bf480e24c06d"; } 
                        attribute :>> interfaceName = "PL 1"; 
                         
                    }  
                    interface '9c2a5261-9743-49e8-9eb4-bf2a657193f1' : PhysicalLink 
                        connect sourcePhysicalPort ::> 'P Wing'.'PP 1'
                        to targetPhysicalPort ::> 'Fuselage'.'PP 8' {
                        @CapellaID { eid = "9c2a5261-9743-49e8-9eb4-bf2a657193f1"; } 
                        attribute :>> interfaceName = "PL 5"; 
                         
                    }  
                    interface '7a43af87-5d93-45ac-b84e-ddc3dc698a23' : PhysicalLink 
                        connect sourcePhysicalPort ::> 'Object Recognition System'.'PP 1'
                        to targetPhysicalPort ::> 'FLIR'.'PP 1' {
                        @CapellaID { eid = "7a43af87-5d93-45ac-b84e-ddc3dc698a23"; sid = "7a43af87-5d93-45ac-b84e-ddc3dc698a23"; } 
                        attribute :>> interfaceName = "Video Connection"; 
                         
                         
                    }  
                    interface 'f19804ff-4f9e-4391-bcf0-52e0fb021778' : PhysicalLink 
                        connect sourcePhysicalPort ::> 'COM LInk'.'PP 1'
                        to targetPhysicalPort ::> 'Object Recognition System'.'PP 2' {
                        @CapellaID { eid = "f19804ff-4f9e-4391-bcf0-52e0fb021778"; sid = "f19804ff-4f9e-4391-bcf0-52e0fb021778"; } 
                        attribute :>> interfaceName = "Video Bus"; 
                         
                         
                    }  
                    interface 'c245d353-cffe-4074-9340-9e4a1f8c97f9' : PhysicalLink 
                        connect sourcePhysicalPort ::> 'Object Recognition System'.'PP 3'
                        to targetPhysicalPort ::> 'Mission Computer'.'PP 1' {
                        @CapellaID { eid = "c245d353-cffe-4074-9340-9e4a1f8c97f9"; sid = "c245d353-cffe-4074-9340-9e4a1f8c97f9"; } 
                        attribute :>> interfaceName = "PL 8"; 
                         
                         
                    }  
                    interface 'af3272c2-9517-4446-8782-14d856630fdf' : PhysicalLink 
                        connect sourcePhysicalPort ::> 'Avionics Control'.'PP 1'
                        to targetPhysicalPort ::> 'Braking System Control Unit (BSCU)'.'PP 3' {
                        @CapellaID { eid = "af3272c2-9517-4446-8782-14d856630fdf"; } 
                        attribute :>> interfaceName = "Cable"; 
                         
                    }  
                    interface 'b349d104-4e67-4fcd-832b-a1219326ec5f' : PhysicalLink 
                        connect sourcePhysicalPort ::> 'Hydralic Reservoir'.'PP 1'
                        to targetPhysicalPort ::> 'Braking Hydralulic Subsystem'.'Blue Hydraulic Pump'.'Fluid In' {
                        @CapellaID { eid = "b349d104-4e67-4fcd-832b-a1219326ec5f"; } 
                        attribute :>> interfaceName = "Hydraulic"; 
                         
                    }  
                    interface '8a8e31ff-2b82-44bb-a81c-3dbcc3a24ad1' : PhysicalLink 
                        connect sourcePhysicalPort ::> 'Hydralic Reservoir'.'PP 2'
                        to targetPhysicalPort ::> 'Braking System Control Unit (BSCU)'.'PP 4' {
                        @CapellaID { eid = "8a8e31ff-2b82-44bb-a81c-3dbcc3a24ad1"; } 
                        attribute :>> interfaceName = "Cable"; 
                         
                    }  
                    interface '82fcee3b-38d7-4d08-baee-9cf9be22e5fc' : PhysicalLink 
                        connect sourcePhysicalPort ::> 'Braking System Control Unit (BSCU)'.'PP 5'
                        to targetPhysicalPort ::> 'Braking Hydralulic Subsystem'.'Shutoff Valve'.'Control In' {
                        @CapellaID { eid = "82fcee3b-38d7-4d08-baee-9cf9be22e5fc"; } 
                        attribute :>> interfaceName = "Cablle"; 
                         
                    }  
                    interface '8318ef2b-e36d-4da4-8fe5-44106d772bc7' : PhysicalLink 
                        connect sourcePhysicalPort ::> 'Hydralic Reservoir'.'PP 1'
                        to targetPhysicalPort ::> 'Braking Hydralulic Subsystem'.'Green Hydraulic Pump'.'Fluid In' {
                        @CapellaID { eid = "8318ef2b-e36d-4da4-8fe5-44106d772bc7"; } 
                        attribute :>> interfaceName = "PL 16"; 
                         
                    }  
                    interface 'b23e70fa-3b8a-4624-ad4f-057491f43f46' : PhysicalLink 
                        connect sourcePhysicalPort ::> 'ion '.'PP 1'
                        to targetPhysicalPort ::> 'Nose Landing Gear'.'NLG  Actuator'.'PP 1' {
                        @CapellaID { eid = "b23e70fa-3b8a-4624-ad4f-057491f43f46"; sid = "b23e70fa-3b8a-4624-ad4f-057491f43f46"; } 
                        attribute :>> interfaceName = "NLG Selector Valve to Actuator"; 
                         
                         
                    }  
                    interface 'ca0dd27f-a1a9-4b74-8215-5719fe40b79f' : PhysicalLink 
                        connect sourcePhysicalPort ::> 'Nose Landing Gear'.'NLG  Actuator'.'PP 2'
                        to targetPhysicalPort ::> 'Nose Landing Gear'.'NLG Wheel Housing and Assembly'.'PP 1' {
                        @CapellaID { eid = "ca0dd27f-a1a9-4b74-8215-5719fe40b79f"; sid = "ca0dd27f-a1a9-4b74-8215-5719fe40b79f"; } 
                        attribute :>> interfaceName = "M-Act to NLGH"; 
                         
                         
                    }  
                    interface '395e6810-cffb-4919-8008-92f30f357ad7' : PhysicalLink 
                        connect sourcePhysicalPort ::> 'Nose Landing Gear'.'NLG Door Selector Valve'.'PP 2'
                        to targetPhysicalPort ::> 'Nose Landing Gear'.'NLG Doors Dump Valve'.'PP 1' {
                        @CapellaID { eid = "395e6810-cffb-4919-8008-92f30f357ad7"; sid = "395e6810-cffb-4919-8008-92f30f357ad7"; } 
                        attribute :>> interfaceName = "NLG Door Selector Valve to NLG Doors Dump Valve"; 
                         
                         
                    }  
                    interface '96356375-49e5-4304-b22a-14a1cc1304e0' : PhysicalLink 
                        connect sourcePhysicalPort ::> 'Nose Landing Gear'.'NLG Door Actuator'.'PP 2'
                        to targetPhysicalPort ::> 'Nose Landing Gear'.'NLG Door Sensor'.'PP 1' {
                        @CapellaID { eid = "96356375-49e5-4304-b22a-14a1cc1304e0"; sid = "96356375-49e5-4304-b22a-14a1cc1304e0"; } 
                        attribute :>> interfaceName = "Door Actuator to Door Sensor"; 
                         
                    }  
                    interface 'eedd256a-a3c4-450d-8ccb-db7369e4ba52' : PhysicalLink 
                        connect sourcePhysicalPort ::> 'Nose Landing Gear'.'NLG Door Sensor'.'PP 2'
                        to targetPhysicalPort ::> 'Nose Landing Gear'.'Landing Gear Control and Indication Computer'.'PP 1' {
                        @CapellaID { eid = "eedd256a-a3c4-450d-8ccb-db7369e4ba52"; sid = "eedd256a-a3c4-450d-8ccb-db7369e4ba52"; } 
                        attribute :>> interfaceName = "NLG Door Sensor"; 
                         
                    }  
                    interface '2b682a60-2255-4398-960e-b0efae8b171a' : PhysicalLink 
                        connect sourcePhysicalPort ::> 'Nose Landing Gear'.'NLG Uplock Sensor 1'.'NLG Downlock Sensor 1'.'PP 2'
                        to targetPhysicalPort ::> 'Nose Landing Gear'.'Landing Gear Control and Indication Computer'.'PP 2' {
                        @CapellaID { eid = "2b682a60-2255-4398-960e-b0efae8b171a"; sid = "2b682a60-2255-4398-960e-b0efae8b171a"; } 
                        attribute :>> interfaceName = "NGL Down Lock 1"; 
                         
                    }  
                    interface 'bdba5466-7d6a-4c30-beee-46bc7c9d14de' : PhysicalLink 
                        connect sourcePhysicalPort ::> 'Nose Landing Gear'.'Landing Gear Control and Indication Computer'.'PP 3'
                        to targetPhysicalPort ::> 'Nose Landing Gear'.'NLG Downlock Sensor 2'.'PP 2' {
                        @CapellaID { eid = "bdba5466-7d6a-4c30-beee-46bc7c9d14de"; sid = "bdba5466-7d6a-4c30-beee-46bc7c9d14de"; } 
                        attribute :>> interfaceName = "NGL Down Lock 1"; 
                         
                    }  
                    interface 'ba51e4b7-b4cd-4ddf-bcce-ebb357374da6' : PhysicalLink 
                        connect sourcePhysicalPort ::> 'Nose Landing Gear'.'NLG Uplock Sensor 2'.'PP 2'
                        to targetPhysicalPort ::> 'Nose Landing Gear'.'Landing Gear Control and Indication Computer'.'PP 4' {
                        @CapellaID { eid = "ba51e4b7-b4cd-4ddf-bcce-ebb357374da6"; sid = "ba51e4b7-b4cd-4ddf-bcce-ebb357374da6"; } 
                        attribute :>> interfaceName = "NGL Uplock Sensor 1"; 
                         
                    }  
                    interface 'b9a7d908-2ac4-4aac-b1b5-a92e7086c454' : PhysicalLink 
                        connect sourcePhysicalPort ::> 'Nose Landing Gear'.'NLG Uplock Sensor 1'.'PP 2'
                        to targetPhysicalPort ::> 'Nose Landing Gear'.'Landing Gear Control and Indication Computer'.'PP 5' {
                        @CapellaID { eid = "b9a7d908-2ac4-4aac-b1b5-a92e7086c454"; sid = "b9a7d908-2ac4-4aac-b1b5-a92e7086c454"; } 
                        attribute :>> interfaceName = "NGL Uplock Sensor 1"; 
                         
                    }  
                    interface 'fec5b940-e96a-422c-9a05-f0c7f34f6b9a' : PhysicalLink 
                        connect sourcePhysicalPort ::> 'Nose Landing Gear'.'NLG Wheel Housing and Assembly'.'PP 3'
                        to targetPhysicalPort ::> 'Nose Landing Gear'.'NLG Shock Absorber'.'PP 1' {
                        @CapellaID { eid = "fec5b940-e96a-422c-9a05-f0c7f34f6b9a"; sid = "fec5b940-e96a-422c-9a05-f0c7f34f6b9a"; } 
                        attribute :>> interfaceName = "Wheel Housing to Shock Absorber"; 
                         
                         
                    }  
                    interface 'f418ca74-6ea7-4077-811d-71240598eac9' : PhysicalLink 
                        connect sourcePhysicalPort ::> 'Nose Landing Gear'.'NLG Wheel Housing and Assembly'.'PP 4'
                        to targetPhysicalPort ::> 'Nose Landing Gear'.'NLG Structural Post Assembly'.'PP 3' {
                        @CapellaID { eid = "f418ca74-6ea7-4077-811d-71240598eac9"; sid = "f418ca74-6ea7-4077-811d-71240598eac9"; } 
                        attribute :>> interfaceName = "Wheel Housing to Structural Post"; 
                         
                         
                    }  
                    interface '3b89e63d-6786-4c3f-8bc6-9632e01d2a43' : PhysicalLink 
                        connect sourcePhysicalPort ::> 'Nose Landing Gear'.'NLG Shock Absorber'.'PP 2'
                        to targetPhysicalPort ::> 'Nose Landing Gear'.'Weight on Wheel Sensor 1'.'PP 1' {
                        @CapellaID { eid = "3b89e63d-6786-4c3f-8bc6-9632e01d2a43"; sid = "3b89e63d-6786-4c3f-8bc6-9632e01d2a43"; } 
                        attribute :>> interfaceName = "Wow1 to Shock"; 
                         
                    }  
                    interface '36d6adb2-ee96-4e21-a0e7-f57a45031268' : PhysicalLink 
                        connect sourcePhysicalPort ::> 'Nose Landing Gear'.'NLG Shock Absorber'.'PP 3'
                        to targetPhysicalPort ::> 'Nose Landing Gear'.'Weight on Wheel Sensor 2'.'PP 1' {
                        @CapellaID { eid = "36d6adb2-ee96-4e21-a0e7-f57a45031268"; sid = "36d6adb2-ee96-4e21-a0e7-f57a45031268"; } 
                        attribute :>> interfaceName = "WoW 2 to Shock"; 
                        ref :>> appliedPropertyValues =  ('Data'::'BUSTYPE'); 
                         
                    }  
                    interface 'e4ec108d-73f8-4555-954d-076584588e01' : PhysicalLink 
                        connect sourcePhysicalPort ::> 'Nose Landing Gear'.'Weight on Wheel Sensor 2'.'PP 2'
                        to targetPhysicalPort ::> 'Nose Landing Gear'.'Landing Gear Control and Indication Computer'.'PP 7' {
                        @CapellaID { eid = "e4ec108d-73f8-4555-954d-076584588e01"; sid = "e4ec108d-73f8-4555-954d-076584588e01"; } 
                        attribute :>> interfaceName = "Weight on Wheel Sensor 2"; 
                         
                    }  
                    interface '6a6fcd77-7be5-4b5d-a460-7b232ccc5c12' : PhysicalLink 
                        connect sourcePhysicalPort ::> 'Hydraulic '.'PP 1'
                        to targetPhysicalPort ::> 'ion '.'PP 2' {
                        @CapellaID { eid = "6a6fcd77-7be5-4b5d-a460-7b232ccc5c12"; sid = "6a6fcd77-7be5-4b5d-a460-7b232ccc5c12"; } 
                        attribute :>> interfaceName = "Hydraulic No. 3"; 
                         
                         
                    }  
                    interface '2d927448-849b-48b6-ae7c-55167bfdede6' : PhysicalLink 
                        connect sourcePhysicalPort ::> 'Nose Landing Gear'.'NLG Structural Post Assembly'.'PP 4'
                        to targetPhysicalPort ::> 'Airframe'.'PP 1' {
                        @CapellaID { eid = "2d927448-849b-48b6-ae7c-55167bfdede6"; sid = "2d927448-849b-48b6-ae7c-55167bfdede6"; } 
                        attribute :>> interfaceName = "Structural Post to Airframe"; 
                         
                         
                    }  
                    interface '6ddfcfe7-a8b2-4252-9e11-cb6e309a9cdb' : PhysicalLink 
                        connect sourcePhysicalPort ::> 'Hydraulic '.'PP 1'
                        to targetPhysicalPort ::> 'Nose Landing Gear'.'NLG Door Selector Valve'.'PP 1' {
                        @CapellaID { eid = "6ddfcfe7-a8b2-4252-9e11-cb6e309a9cdb"; sid = "6ddfcfe7-a8b2-4252-9e11-cb6e309a9cdb"; } 
                        attribute :>> interfaceName = "Hydraulic No. 3"; 
                         
                         
                    }  
                    interface '282e8334-5b1c-46f6-a1bf-2c467cb80c74' : PhysicalLink 
                        connect sourcePhysicalPort ::> 'Braking Hydralulic Subsystem'.'Junction'.'Geatr Out'
                        to targetPhysicalPort ::> 'Nose Landing Gear'.'NLG Wheel Housing and Assembly'.'PP 2' {
                        @CapellaID { eid = "282e8334-5b1c-46f6-a1bf-2c467cb80c74"; sid = "282e8334-5b1c-46f6-a1bf-2c467cb80c74"; } 
                        attribute :>> interfaceName = "Junction to Wheel Housing"; 
                         
                    }  
                    interface '816058c7-de67-43f8-95b3-4b90d91e0929' : PhysicalLink 
                        connect sourcePhysicalPort ::> 'Nose Landing Gear'.'Landing Gear Control and Indication Computer'.'PP 8'
                        to targetPhysicalPort ::> 'ion '.'PP 3' {
                        @CapellaID { eid = "816058c7-de67-43f8-95b3-4b90d91e0929"; } 
                        attribute :>> interfaceName = "NLG Command"; 
                         
                    }  
                    interface 'e23c07ab-8745-4c18-a4cd-d3e8416e973b' : PhysicalLink 
                        connect sourcePhysicalPort ::> 'Nose Landing Gear'.'Landing Gear Control and Indication Computer'.'PP 6'
                        to targetPhysicalPort ::> 'Port Com Bus'.'PP 1' {
                        @CapellaID { eid = "e23c07ab-8745-4c18-a4cd-d3e8416e973b"; } 
                        attribute :>> interfaceName = "LGCIU to Com Bus"; 
                         
                    }  
                    interface 'f1e3cd51-e931-4b3d-b700-0127f9d4c160' : PhysicalLink 
                        connect sourcePhysicalPort ::> 'Nose Landing Gear'.'Weight on Wheel Sensor 1'.'PP 2'
                        to targetPhysicalPort ::> 'Port Com Bus'.'PP 2' {
                        @CapellaID { eid = "f1e3cd51-e931-4b3d-b700-0127f9d4c160"; } 
                        attribute :>> interfaceName = "WoW Sensor 1 to Com Bus"; 
                         
                    }  
                    interface 'a9948a56-74c0-4995-81e5-d2c98d932cf4' : PhysicalLink 
                        connect sourcePhysicalPort ::> 'Nose Landing Gear'.'NLG Door Actuator'.'PP 3'
                        to targetPhysicalPort ::> 'NLG Door'.'PP 1' {
                        @CapellaID { eid = "a9948a56-74c0-4995-81e5-d2c98d932cf4"; } 
                        attribute :>> interfaceName = "M-NLG Door Act to Door"; 
                         
                         
                    }  
                    interface '08832afb-1cd5-4e60-be8d-568ead6919ef' : PhysicalLink 
                        connect sourcePhysicalPort ::> 'Airframe'.'PP 2'
                        to targetPhysicalPort ::> 'NLG Door'.'PP 2' {
                        @CapellaID { eid = "08832afb-1cd5-4e60-be8d-568ead6919ef"; } 
                        attribute :>> interfaceName = "M-AF to NLG Door"; 
                         
                         
                    }  
                    interface 'c8138675-339c-4feb-a1ae-06cd45a2b27e' : PhysicalLink 
                        connect sourcePhysicalPort ::> 'Pilot Interface'.'PP 4'
                        to targetPhysicalPort ::> 'Nose Landing Gear'.'Landing Gear Control and Indication Computer'.'PP 9' {
                        @CapellaID { eid = "c8138675-339c-4feb-a1ae-06cd45a2b27e"; } 
                        attribute :>> interfaceName = "E-PI to LGC"; 
                         
                    }  
                    interface '10405803-2fc0-4274-8743-1356a041ff0d' : PhysicalLink 
                        connect sourcePhysicalPort ::> 'Pilot Interface'.'PP 5'
                        to targetPhysicalPort ::> 'Nose Landing Gear'.'NLG Doors Dump Valve'.'PP 2' {
                        @CapellaID { eid = "10405803-2fc0-4274-8743-1356a041ff0d"; } 
                        attribute :>> interfaceName = "M-NLG Door Dump"; 
                         
                         
                    }  
                    interface 'e744dc5f-bfce-407c-bfe7-99ba2b2681cb' : PhysicalLink 
                        connect sourcePhysicalPort ::> 'Pilot Interface'.'PP 6'
                        to targetPhysicalPort ::> 'NLG Dump Valve'.'PP 4' {
                        @CapellaID { eid = "e744dc5f-bfce-407c-bfe7-99ba2b2681cb"; } 
                        attribute :>> interfaceName = "M-NLG Dump"; 
                         
                         
                    }  
                    interface '367c22c4-34dd-411b-9759-827ea0f57faa' : PhysicalLink 
                        connect sourcePhysicalPort ::> 'Nose Landing Gear'.'NLG Doors Dump Valve'.'PP 3'
                        to targetPhysicalPort ::> 'H Reservoir'.'PP 1' {
                        @CapellaID { eid = "367c22c4-34dd-411b-9759-827ea0f57faa"; } 
                        attribute :>> interfaceName = "Dump Valve to Reservoir"; 
                         
                         
                    }  
                    interface 'da7523c5-bff4-4391-91ee-4a405df67805' : PhysicalLink 
                        connect sourcePhysicalPort ::> 'H2'.'PP 1'
                        to targetPhysicalPort ::> 'H Reservoir'.'PP 2' {
                        @CapellaID { eid = "da7523c5-bff4-4391-91ee-4a405df67805"; } 
                        attribute :>> interfaceName = "H2 to H Reservoir"; 
                         
                         
                    }  
                    interface 'e9a13f8c-dc13-470a-abbb-c545e5ab8fd3' : PhysicalLink 
                        connect sourcePhysicalPort ::> 'H3'.'PP 1'
                        to targetPhysicalPort ::> 'H2'.'PP 2' {
                        @CapellaID { eid = "e9a13f8c-dc13-470a-abbb-c545e5ab8fd3"; } 
                        attribute :>> interfaceName = "H3 to H2"; 
                         
                         
                    }  
                    interface '4ef2f4af-a216-46f4-9225-d1e6a21cc536' : PhysicalLink 
                        connect sourcePhysicalPort ::> 'H3'.'PP 2'
                        to targetPhysicalPort ::> 'Hydraulic '.'PP 2' {
                        @CapellaID { eid = "4ef2f4af-a216-46f4-9225-d1e6a21cc536"; } 
                        attribute :>> interfaceName = "H3 to Hydraulic"; 
                         
                         
                    }  
                    interface 'f4fb3042-bbcb-4e55-95ae-e676e8dcb408' : PhysicalLink 
                        connect sourcePhysicalPort ::> 'H Reservoir'.'PP 3'
                        to targetPhysicalPort ::> 'H3'.'PP 3' {
                        @CapellaID { eid = "f4fb3042-bbcb-4e55-95ae-e676e8dcb408"; } 
                        attribute :>> interfaceName = "H Reservoir to H3"; 
                         
                         
                    }  
                    interface 'bc30689c-c382-4ea9-a33a-ac16501498ed' : PhysicalLink 
                        connect sourcePhysicalPort ::> 'ion '.'PP 5'
                        to targetPhysicalPort ::> 'NLG Dump Valve'.'PP 5' {
                        @CapellaID { eid = "bc30689c-c382-4ea9-a33a-ac16501498ed"; } 
                        attribute :>> interfaceName = "NLG Selector Valve to NLG Dump Valve"; 
                         
                         
                    }  
                    interface 'fdee7afb-3707-4375-a8f4-5cfbddb14d49' : PhysicalLink 
                        connect sourcePhysicalPort ::> 'NLG Dump Valve'.'PP 6'
                        to targetPhysicalPort ::> 'H Reservoir'.'PP 4' {
                        @CapellaID { eid = "fdee7afb-3707-4375-a8f4-5cfbddb14d49"; } 
                        attribute :>> interfaceName = "NLG Dump Valve to H Reservoir"; 
                         
                         
                    }  
                    part 'Aerial Platform' : PhysicalComponent { 
                        @CapellaID { eid = "30e6e6ca-f3a1-487c-a6eb-f6374c8fc811"; } 
                        attribute :>> isAbstract = false; 
                        attribute :>> isActor = false; 
                        attribute :>> isHuman = false; 
                        attribute :>> kind = PhysicalComponentKind::UNSET; 
                        attribute :>> nature = PhysicalComponentNature::NODE; 
                         
                    }  
                    part 'Ground System' : PhysicalComponent { 
                        @CapellaID { eid = "cd7fd967-fe32-4aac-b46a-38d4fe59db02"; } 
                        attribute :>> isAbstract = false; 
                        attribute :>> isActor = false; 
                        attribute :>> isHuman = false; 
                        attribute :>> kind = PhysicalComponentKind::UNSET; 
                        attribute :>> nature = PhysicalComponentNature::NODE; 
                         
                    }  
                    part 'Up Link' : PhysicalComponent { 
                        @CapellaID { eid = "2fe482eb-33f2-4a7a-a3ec-aadb0910b34d"; } 
                        attribute :>> isAbstract = false; 
                        attribute :>> isActor = false; 
                        attribute :>> isHuman = false; 
                        attribute :>> kind = PhysicalComponentKind::UNSET; 
                        attribute :>> nature = PhysicalComponentNature::NODE; 
                         
                    }  
                    part 'Satellite' : PhysicalComponent { 
                        @CapellaID { eid = "c62dd6e7-9c9d-4304-a19f-39d3ec28fb66"; } 
                        attribute :>> isAbstract = false; 
                        attribute :>> isActor = false; 
                        attribute :>> isHuman = false; 
                        attribute :>> kind = PhysicalComponentKind::UNSET; 
                        attribute :>> nature = PhysicalComponentNature::NODE; 
                         
                    }  
                    part 'Avionics' : PhysicalComponent { 
                        @CapellaID { eid = "acf6e0a7-f15f-46a8-a9ef-b51a104778af"; } 
                        attribute :>> isAbstract = false; 
                        attribute :>> isActor = false; 
                        attribute :>> isHuman = false; 
                        attribute :>> kind = PhysicalComponentKind::UNSET; 
                        attribute :>> nature = PhysicalComponentNature::NODE; 
                        part 'd991eea4-db3e-460a-9426-b4a74c385155' : CPart :> 'Communications'  { 
                            @CapellaID { eid = "d991eea4-db3e-460a-9426-b4a74c385155"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '5f0efe5d-2eed-4dee-9efb-a29cbebb6861' : CPart :> 'Auto Flight Control'  { 
                            @CapellaID { eid = "5f0efe5d-2eed-4dee-9efb-a29cbebb6861"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '606ea5fc-76ad-46d9-b08d-f9e6b3a707b8' : CPart :> 'Health Monitoring'  { 
                            @CapellaID { eid = "606ea5fc-76ad-46d9-b08d-f9e6b3a707b8"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '60d8dd7e-af72-4743-9393-0ed801d3034b' : CPart :> 'Stores Management'  { 
                            @CapellaID { eid = "60d8dd7e-af72-4743-9393-0ed801d3034b"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'f1a8695b-9e70-44f1-a274-9dd5cb4fa811' : CPart :> 'Nav / Guidance'  { 
                            @CapellaID { eid = "f1a8695b-9e70-44f1-a274-9dd5cb4fa811"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '3de6c622-5933-4dd3-bd43-f1a0c4802c38' : CPart :> 'Mission Data CPU'  { 
                            @CapellaID { eid = "3de6c622-5933-4dd3-bd43-f1a0c4802c38"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 7' : PhysicalPort { 
                            @CapellaID { eid = "eca7ef6a-8723-4608-9dc3-f586b58446eb"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'Communications' : PhysicalComponent { 
                            @CapellaID { eid = "71b701bd-9583-409a-8763-ab2885055fd6"; } 
                            attribute :>> isAbstract = false; 
                            attribute :>> isActor = false; 
                            attribute :>> isHuman = false; 
                            attribute :>> kind = PhysicalComponentKind::UNSET; 
                            attribute :>> nature = PhysicalComponentNature::NODE; 
                             
                        }  
                        part 'Auto Flight Control' : PhysicalComponent { 
                            @CapellaID { eid = "77a60550-57aa-49d7-a457-60231538af2d"; } 
                            attribute :>> isAbstract = false; 
                            attribute :>> isActor = false; 
                            attribute :>> isHuman = false; 
                            attribute :>> kind = PhysicalComponentKind::UNSET; 
                            attribute :>> nature = PhysicalComponentNature::NODE; 
                             
                        }  
                        part 'Health Monitoring' : PhysicalComponent { 
                            @CapellaID { eid = "cddf94ad-0c18-4001-9334-4a61b000c292"; } 
                            attribute :>> isAbstract = false; 
                            attribute :>> isActor = false; 
                            attribute :>> isHuman = false; 
                            attribute :>> kind = PhysicalComponentKind::UNSET; 
                            attribute :>> nature = PhysicalComponentNature::NODE; 
                             
                        }  
                        part 'Stores Management' : PhysicalComponent { 
                            @CapellaID { eid = "da07f0f6-2c9a-43c2-aa24-7f8335cb7655"; } 
                            attribute :>> isAbstract = false; 
                            attribute :>> isActor = false; 
                            attribute :>> isHuman = false; 
                            attribute :>> kind = PhysicalComponentKind::UNSET; 
                            attribute :>> nature = PhysicalComponentNature::NODE; 
                             
                        }  
                        part 'Nav / Guidance' : PhysicalComponent { 
                            @CapellaID { eid = "e8420fa7-461d-4068-bdd9-8c357d2ca28d"; } 
                            attribute :>> isAbstract = false; 
                            attribute :>> isActor = false; 
                            attribute :>> isHuman = false; 
                            attribute :>> kind = PhysicalComponentKind::UNSET; 
                            attribute :>> nature = PhysicalComponentNature::NODE; 
                             
                        }  
                        part 'Mission Data CPU' : PhysicalComponent { 
                            @CapellaID { eid = "2dae0afa-3e03-4407-8f62-2ef04e4744eb"; } 
                            attribute :>> isAbstract = false; 
                            attribute :>> isActor = false; 
                            attribute :>> isHuman = false; 
                            attribute :>> kind = PhysicalComponentKind::UNSET; 
                            attribute :>> nature = PhysicalComponentNature::NODE; 
                             
                        }  
                         
                        ref :>> ownedPhysicalComponents =  ('Communications',
                        'Auto Flight Control',
                        'Health Monitoring',
                        'Stores Management',
                        'Nav / Guidance',
                        'Mission Data CPU'); 
                    }  
                    part 'Vehicle Subsystems' : PhysicalComponent { 
                        @CapellaID { eid = "432f0aa0-3111-4170-aa21-0ef41447995a"; } 
                        attribute :>> isAbstract = false; 
                        attribute :>> isActor = false; 
                        attribute :>> isHuman = false; 
                        attribute :>> kind = PhysicalComponentKind::UNSET; 
                        attribute :>> nature = PhysicalComponentNature::NODE; 
                        part 'cfe60894-3fcb-410b-908d-ea9a3ead0ed4' : CPart :> 'Flight Control'  { 
                            @CapellaID { eid = "cfe60894-3fcb-410b-908d-ea9a3ead0ed4"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'b4ee3c89-2551-48ba-b38d-b409bad27d80' : CPart :> 'Hydraulics'  { 
                            @CapellaID { eid = "b4ee3c89-2551-48ba-b38d-b409bad27d80"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '572561eb-20dd-4990-83a7-df34be6f4e3d' : CPart :> 'Environmental Control'  { 
                            @CapellaID { eid = "572561eb-20dd-4990-83a7-df34be6f4e3d"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '984c9bbc-32a7-44e2-8791-a091d11c3fc7' : CPart :> 'Landing Gear'  { 
                            @CapellaID { eid = "984c9bbc-32a7-44e2-8791-a091d11c3fc7"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'd686a7de-4388-4e90-8765-b779d09f6a28' : CPart :> 'Aux Power'  { 
                            @CapellaID { eid = "d686a7de-4388-4e90-8765-b779d09f6a28"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '222ec201-5ef6-450c-9dc1-a5925af59d01' : CPart :> 'Electrical'  { 
                            @CapellaID { eid = "222ec201-5ef6-450c-9dc1-a5925af59d01"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '59515c82-4b42-41a8-ac3b-217a433c33ab' : CPart :> 'Fuel'  { 
                            @CapellaID { eid = "59515c82-4b42-41a8-ac3b-217a433c33ab"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'e739fff8-fa67-4977-b5e0-2d1e39197313' : CPart :> 'Software'  { 
                            @CapellaID { eid = "e739fff8-fa67-4977-b5e0-2d1e39197313"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 9' : PhysicalPort { 
                            @CapellaID { eid = "894c6450-a083-4f9d-b1f5-c4ce2c370e5a"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'Flight Control' : PhysicalComponent { 
                            @CapellaID { eid = "4c2dddbf-7387-4610-9878-be37b3c2a583"; } 
                            attribute :>> isAbstract = false; 
                            attribute :>> isActor = false; 
                            attribute :>> isHuman = false; 
                            attribute :>> kind = PhysicalComponentKind::UNSET; 
                            attribute :>> nature = PhysicalComponentNature::NODE; 
                             
                        }  
                        part 'Hydraulics' : PhysicalComponent { 
                            @CapellaID { eid = "2e273dbd-fda2-498d-a896-2a6dc5cd8179"; } 
                            attribute :>> isAbstract = false; 
                            attribute :>> isActor = false; 
                            attribute :>> isHuman = false; 
                            attribute :>> kind = PhysicalComponentKind::UNSET; 
                            attribute :>> nature = PhysicalComponentNature::NODE; 
                             
                        }  
                        part 'Environmental Control' : PhysicalComponent { 
                            @CapellaID { eid = "691b9ccb-c904-4b4d-8450-30e46c55ad73"; } 
                            attribute :>> isAbstract = false; 
                            attribute :>> isActor = false; 
                            attribute :>> isHuman = false; 
                            attribute :>> kind = PhysicalComponentKind::UNSET; 
                            attribute :>> nature = PhysicalComponentNature::NODE; 
                             
                        }  
                        part 'Landing Gear' : PhysicalComponent { 
                            @CapellaID { eid = "9bbf874a-5fce-43e4-9e81-553211040390"; } 
                            attribute :>> isAbstract = false; 
                            attribute :>> isActor = false; 
                            attribute :>> isHuman = false; 
                            attribute :>> kind = PhysicalComponentKind::UNSET; 
                            attribute :>> nature = PhysicalComponentNature::NODE; 
                             
                        }  
                        part 'Aux Power' : PhysicalComponent { 
                            @CapellaID { eid = "b9a47fc3-87a9-41f4-860a-cf158fec5ef2"; } 
                            attribute :>> isAbstract = false; 
                            attribute :>> isActor = false; 
                            attribute :>> isHuman = false; 
                            attribute :>> kind = PhysicalComponentKind::UNSET; 
                            attribute :>> nature = PhysicalComponentNature::NODE; 
                             
                        }  
                        part 'Electrical' : PhysicalComponent { 
                            @CapellaID { eid = "f834da1d-21bf-4882-aef9-f90e309b57d7"; } 
                            attribute :>> isAbstract = false; 
                            attribute :>> isActor = false; 
                            attribute :>> isHuman = false; 
                            attribute :>> kind = PhysicalComponentKind::UNSET; 
                            attribute :>> nature = PhysicalComponentNature::NODE; 
                             
                        }  
                        part 'Fuel' : PhysicalComponent { 
                            @CapellaID { eid = "80543adb-fc16-451d-a773-faa5de4274d5"; } 
                            attribute :>> isAbstract = false; 
                            attribute :>> isActor = false; 
                            attribute :>> isHuman = false; 
                            attribute :>> kind = PhysicalComponentKind::UNSET; 
                            attribute :>> nature = PhysicalComponentNature::NODE; 
                             
                        }  
                        part 'Software' : PhysicalComponent { 
                            @CapellaID { eid = "fb927461-5d5c-4784-a516-2aa3064e1e03"; } 
                            attribute :>> isAbstract = false; 
                            attribute :>> isActor = false; 
                            attribute :>> isHuman = false; 
                            attribute :>> kind = PhysicalComponentKind::UNSET; 
                            attribute :>> nature = PhysicalComponentNature::NODE; 
                             
                        }  
                         
                        ref :>> ownedPhysicalComponents =  ('Flight Control',
                        'Hydraulics',
                        'Environmental Control',
                        'Landing Gear',
                        'Aux Power',
                        'Electrical',
                        'Fuel',
                        'Software'); 
                    }  
                    part 'Propulsion' : PhysicalComponent { 
                        @CapellaID { eid = "ab76291b-fbb4-4430-9439-7bc58fb2191f"; } 
                        attribute :>> isAbstract = false; 
                        attribute :>> isActor = false; 
                        attribute :>> isHuman = false; 
                        attribute :>> kind = PhysicalComponentKind::UNSET; 
                        attribute :>> nature = PhysicalComponentNature::NODE; 
                        part '091ff20f-1d78-44ce-ab0c-5466426fca1d' : CPart :> 'Engine'  { 
                            @CapellaID { eid = "091ff20f-1d78-44ce-ab0c-5466426fca1d"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 1' : PhysicalPort { 
                            @CapellaID { eid = "193a04ee-ca61-417f-8930-1c799f5d6143"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'Engine' : PhysicalComponent { 
                            @CapellaID { eid = "5f27f410-65c3-4111-bb57-8fa768dbe8df"; } 
                            attribute :>> isAbstract = false; 
                            attribute :>> isActor = false; 
                            attribute :>> isHuman = false; 
                            attribute :>> kind = PhysicalComponentKind::UNSET; 
                            attribute :>> nature = PhysicalComponentNature::NODE; 
                             
                        }  
                         
                        ref :>> ownedPhysicalComponents =  ('Engine'); 
                    }  
                    part 'Fuselage' : PhysicalComponent { 
                        @CapellaID { eid = "115fcadb-835a-472b-b46c-47b5166f46ef"; } 
                        attribute :>> isAbstract = false; 
                        attribute :>> isActor = false; 
                        attribute :>> isHuman = false; 
                        attribute :>> kind = PhysicalComponentKind::UNSET; 
                        attribute :>> nature = PhysicalComponentNature::NODE; 
                        port 'PP 2' : PhysicalPort { 
                            @CapellaID { eid = "a7624662-98b7-44a1-adc8-d21f47258eca"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 3' : PhysicalPort { 
                            @CapellaID { eid = "f3a8669d-a254-4d03-b58e-e12c69154e78"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 4' : PhysicalPort { 
                            @CapellaID { eid = "583f6c00-3fa5-488e-bb4e-5a11b1c97909"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 7' : PhysicalPort { 
                            @CapellaID { eid = "57a6c4cc-2983-4714-8d99-e7dfe0c2cad2"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 6' : PhysicalPort { 
                            @CapellaID { eid = "1009cf04-17f6-41d6-8ab2-20a91cd6df06"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 1' : PhysicalPort { 
                            @CapellaID { eid = "a3c5cfd7-8337-4613-9078-2f7cb8133801"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 8' : PhysicalPort { 
                            @CapellaID { eid = "9ab42456-e88c-4001-86f1-d72c4752ab22"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                         
                    }  
                    part 'Empennage' : PhysicalComponent { 
                        @CapellaID { eid = "aa6059b3-fb23-4c07-936f-f66ab8a102a4"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "44e72940-72bd-4df1-8238-602635f53825"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                         
                    }  
                    part 'S Wing' : PhysicalComponent { 
                        @CapellaID { eid = "e28e694d-102b-49e2-a87f-740746f7854b"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "300981a0-22b4-41db-bf33-95768dfe24f6"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                         
                    }  
                    part 'P Wing' : PhysicalComponent { 
                        @CapellaID { eid = "85183dfa-6944-4d7e-96dd-1eb1c2303d2b"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "0a398441-cf83-4bbf-91d1-534fc830a46a"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                         
                    }  
                    part 'Drone' : PhysicalComponent { 
                        @CapellaID { eid = "ac0afaa6-b024-4171-9ff0-ded9b166ebeb"; sid = "f17f94b5-a717-4018-8a61-0ed107f1909f"; } 
                        attribute :>> isAbstract = false; 
                        attribute :>> isActor = false; 
                        attribute :>> isHuman = false; 
                        attribute :>> kind = PhysicalComponentKind::UNSET; 
                        attribute :>> nature = PhysicalComponentNature::NODE; 
                        dependency '8e671b2f-aa6f-4d9b-a93f-d1f33847f302'
                            from 'Nose Landing Gear Library'::'Nose Landing Gear'::'Physical Architecture'::'Structure'::'Physical System'::'Drone'
                            to  'Logical Architecture'::'Structure'::'UAV System'::'Drone BC' { 
                            @JustificationLink { 
                                @CapellaID { eid = "8e671b2f-aa6f-4d9b-a93f-d1f33847f302"; } 
                            }  
                        }  
                        port 'PP 1' : PhysicalPort { 
                            @CapellaID { eid = "9f941311-4fe2-4b25-a9bf-0fc3cdcfba60"; sid = "4f232cfe-c7f6-4df0-8fcc-2d56df91affd"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                             
                        }  
                         
                         
                    }  
                    part 'FLIR' : PhysicalComponent { 
                        @CapellaID { eid = "897800b1-7cac-445a-af30-e828fa1ced71"; sid = "897800b1-7cac-445a-af30-e828fa1ced71"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "329f3717-c604-4bad-9653-7579c534425a"; sid = "329f3717-c604-4bad-9653-7579c534425a"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '8896c17c-07ce-496c-89ee-aa22218b3104' : ComponentPortAllocation
                                allocate allocatedPort ::> 'PP 1'
                                to allocatingPort ::> 'Nose Landing Gear Library'::'Nose Landing Gear'::'Physical Architecture'::'Structure'::'Physical System'.'Behavior Parent'.'Fuel and Power System'.'FLIR'.'CP 1' { 
                                @CapellaID { eid = "8896c17c-07ce-496c-89ee-aa22218b3104"; } 
                                 
                            }  
                             
                            ref :>> ownedComponentPortAllocations =  ('8896c17c-07ce-496c-89ee-aa22218b3104'); 
                        }  
                        port 'PP 2' : PhysicalPort { 
                            @CapellaID { eid = "ff37b45c-4b88-4c8e-b0f8-ab495a3b10be"; sid = "ff37b45c-4b88-4c8e-b0f8-ab495a3b10be"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '99586cec-2e86-4428-a666-836b86274d74' : ComponentPortAllocation
                                allocate allocatedPort ::> 'PP 2'
                                to allocatingPort ::> 'Nose Landing Gear Library'::'Nose Landing Gear'::'Physical Architecture'::'Structure'::'Physical System'.'Behavior Parent'.'Fuel and Power System'.'FLIR'.'CP 2' { 
                                @CapellaID { eid = "99586cec-2e86-4428-a666-836b86274d74"; } 
                                 
                            }  
                             
                            ref :>> ownedComponentPortAllocations =  ('99586cec-2e86-4428-a666-836b86274d74'); 
                        }  
                        port 'PP 3' : PhysicalPort { 
                            @CapellaID { eid = "256f0032-d583-422a-935e-e9eb0b6e3bd0"; sid = "256f0032-d583-422a-935e-e9eb0b6e3bd0"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '9d0480cf-8dc8-47ac-af32-b55d54847dea' : ComponentPortAllocation
                                allocate allocatedPort ::> 'PP 3'
                                to allocatingPort ::> 'Nose Landing Gear Library'::'Nose Landing Gear'::'Physical Architecture'::'Structure'::'Physical System'.'Behavior Parent'.'Fuel and Power System'.'FLIR'.'CP 3' { 
                                @CapellaID { eid = "9d0480cf-8dc8-47ac-af32-b55d54847dea"; } 
                                 
                            }  
                             
                            ref :>> ownedComponentPortAllocations =  ('9d0480cf-8dc8-47ac-af32-b55d54847dea'); 
                        }  
                         
                         
                    }  
                    part 'Object Recognition System' : PhysicalComponent { 
                        @CapellaID { eid = "fa0250a9-67cd-43bc-b480-47a34ccd7ee5"; sid = "fa0250a9-67cd-43bc-b480-47a34ccd7ee5"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "a56354f6-eeeb-4126-84ea-60418ffc1f61"; sid = "a56354f6-eeeb-4126-84ea-60418ffc1f61"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation 'de6f8f5a-2b62-44c3-b4c6-054f41799c9d' : ComponentPortAllocation
                                allocate allocatedPort ::> 'PP 1'
                                to allocatingPort ::> 'Nose Landing Gear Library'::'Nose Landing Gear'::'Physical Architecture'::'Structure'::'Physical System'.'Behavior Parent'.'Fuel and Power System'.'ORS '.'CP 1' { 
                                @CapellaID { eid = "de6f8f5a-2b62-44c3-b4c6-054f41799c9d"; } 
                                 
                            }  
                             
                            ref :>> ownedComponentPortAllocations =  ('de6f8f5a-2b62-44c3-b4c6-054f41799c9d'); 
                        }  
                        port 'PP 2' : PhysicalPort { 
                            @CapellaID { eid = "2a753b32-ebd5-49da-b466-ebfeb0ce9fa9"; sid = "2a753b32-ebd5-49da-b466-ebfeb0ce9fa9"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation 'abb0bc8a-50a0-4bca-ab02-617d898c4e3c' : ComponentPortAllocation
                                allocate allocatedPort ::> 'PP 2'
                                to allocatingPort ::> 'Nose Landing Gear Library'::'Nose Landing Gear'::'Physical Architecture'::'Structure'::'Physical System'.'Behavior Parent'.'Fuel and Power System'.'ORS '.'CP 2' { 
                                @CapellaID { eid = "abb0bc8a-50a0-4bca-ab02-617d898c4e3c"; } 
                                 
                            }  
                             
                            ref :>> ownedComponentPortAllocations =  ('abb0bc8a-50a0-4bca-ab02-617d898c4e3c'); 
                        }  
                        port 'PP 3' : PhysicalPort { 
                            @CapellaID { eid = "de632176-1546-4170-932b-15f7cddc0350"; sid = "de632176-1546-4170-932b-15f7cddc0350"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation 'c290d850-152c-4dff-b039-5f1e1782a7a8' : ComponentPortAllocation
                                allocate allocatedPort ::> 'PP 3'
                                to allocatingPort ::> 'Nose Landing Gear Library'::'Nose Landing Gear'::'Physical Architecture'::'Structure'::'Physical System'.'Behavior Parent'.'Fuel and Power System'.'ORS '.'CP 3' { 
                                @CapellaID { eid = "c290d850-152c-4dff-b039-5f1e1782a7a8"; } 
                                 
                            }  
                             
                            ref :>> ownedComponentPortAllocations =  ('c290d850-152c-4dff-b039-5f1e1782a7a8'); 
                        }  
                         
                         
                    }  
                    part 'COM LInk' : PhysicalComponent { 
                        @CapellaID { eid = "e7e38be7-1228-4f63-ba79-c3d16cb1509d"; sid = "e7e38be7-1228-4f63-ba79-c3d16cb1509d"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "91abdad7-c981-4406-a858-b887f9bc1c86"; sid = "91abdad7-c981-4406-a858-b887f9bc1c86"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '977da683-9bc5-4050-a582-4d2eb425178e' : ComponentPortAllocation
                                allocate allocatedPort ::> 'PP 1'
                                to allocatingPort ::> 'Nose Landing Gear Library'::'Nose Landing Gear'::'Physical Architecture'::'Structure'::'Physical System'.'Behavior Parent'.'ComLink'.'CP 3' { 
                                @CapellaID { eid = "977da683-9bc5-4050-a582-4d2eb425178e"; } 
                                 
                            }  
                             
                            ref :>> ownedComponentPortAllocations =  ('977da683-9bc5-4050-a582-4d2eb425178e'); 
                        }  
                        port 'PP 2' : PhysicalPort { 
                            @CapellaID { eid = "ab59f488-79dc-4598-87e8-14d8af01dcf2"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                         
                         
                    }  
                    part 'Mission Computer' : PhysicalComponent { 
                        @CapellaID { eid = "f04edcff-5688-47dd-b25a-912a57df8bed"; sid = "f04edcff-5688-47dd-b25a-912a57df8bed"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "00ef4807-40fa-4ad9-a3a4-efaad168a5e5"; sid = "00ef4807-40fa-4ad9-a3a4-efaad168a5e5"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation 'bd0a0ee1-2405-4578-bbe2-b081b1755a9d' : ComponentPortAllocation
                                allocate allocatedPort ::> 'PP 1'
                                to allocatingPort ::> 'Nose Landing Gear Library'::'Nose Landing Gear'::'Physical Architecture'::'Structure'::'Physical System'.'Behavior Parent'.'Fuel and Power System'.'MC Comp'.'CP 1' { 
                                @CapellaID { eid = "bd0a0ee1-2405-4578-bbe2-b081b1755a9d"; } 
                                 
                            }  
                             
                            ref :>> ownedComponentPortAllocations =  ('bd0a0ee1-2405-4578-bbe2-b081b1755a9d'); 
                        }  
                         
                    }  
                    part 'Braking System Control Unit (BSCU)' : PhysicalComponent { 
                        @CapellaID { eid = "18fc0a3e-1e84-43d0-b9a8-4ab27e30abe0"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "a28fb6dd-da20-4fb1-ac38-c8fec6d670b9"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 2' : PhysicalPort { 
                            @CapellaID { eid = "6f6c4f96-c681-4ef7-af45-e0b52a2f2819"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 3' : PhysicalPort { 
                            @CapellaID { eid = "14ba81d1-e5fd-4a4b-9464-c04ae7a70db4"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 4' : PhysicalPort { 
                            @CapellaID { eid = "d9d3ee61-533a-43ce-89d8-f03ac43f0f4e"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 5' : PhysicalPort { 
                            @CapellaID { eid = "ca41db12-bcdb-4008-a730-608bd66633b6"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                         
                    }  
                    part 'Hydralic Reservoir' : PhysicalComponent { 
                        @CapellaID { eid = "94c704da-3c10-4062-b25a-14d0e355aad5"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "3f49e39b-e3d5-462c-a203-5c2486e0be7d"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 2' : PhysicalPort { 
                            @CapellaID { eid = "4210376b-e0cc-4489-934a-a9bbf659322e"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                         
                    }  
                    part 'Avionics Control' : PhysicalComponent { 
                        @CapellaID { eid = "c74c286b-e82c-49df-87ff-ec2af68ac936"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "4baa95c4-51ed-4719-8c18-700ac8f7126c"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                         
                    }  
                    part 'Braking Hydralulic Subsystem' : PhysicalComponent { 
                        @CapellaID { eid = "55a80914-2b48-4751-8cb1-0346e64ada75"; sid = "55a80914-2b48-4751-8cb1-0346e64ada75"; } 
                        attribute :>> isAbstract = false; 
                        attribute :>> isActor = false; 
                        attribute :>> isHuman = false; 
                        attribute :>> kind = PhysicalComponentKind::UNSET; 
                        attribute :>> nature = PhysicalComponentNature::NODE; 
                        part 'dde5c9c0-3adf-4728-ad35-3e7054f8af4e' : CPart :> 'Blue Hydraulic Pump'  { 
                            @CapellaID { eid = "dde5c9c0-3adf-4728-ad35-3e7054f8af4e"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation '3e49f8d9-a3cf-4d36-a8fb-c52f6fd10b3b' : PartDeploymentLink
                                allocate deployedElement ::> 'Behavior Parent'.'f936ab29-48bc-4d9e-8fde-e2a35baedfe4'
                                to location ::> 'Nose Landing Gear Library'::'Nose Landing Gear'::'Physical Architecture'::'Structure'::'Physical System'.'Braking Hydralulic Subsystem'.'dde5c9c0-3adf-4728-ad35-3e7054f8af4e' { 
                                @CapellaID { eid = "3e49f8d9-a3cf-4d36-a8fb-c52f6fd10b3b"; } 
                                 
                            }  
                            ref :>> ownedDeploymentLinks =  ('3e49f8d9-a3cf-4d36-a8fb-c52f6fd10b3b'); 
                             
                        }  
                        part 'd5440e45-4c67-44e8-8a0e-0be9d9465144' : CPart :> 'Green Hydraulic Pump'  { 
                            @CapellaID { eid = "d5440e45-4c67-44e8-8a0e-0be9d9465144"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation 'd69ee3bc-dd57-4aef-8906-b86ec0413163' : PartDeploymentLink
                                allocate deployedElement ::> 'Behavior Parent'.'Fuel and Power System'.'aae4ae38-86c3-4743-b346-0301611e1823'
                                to location ::> 'Nose Landing Gear Library'::'Nose Landing Gear'::'Physical Architecture'::'Structure'::'Physical System'.'Braking Hydralulic Subsystem'.'d5440e45-4c67-44e8-8a0e-0be9d9465144' { 
                                @CapellaID { eid = "d69ee3bc-dd57-4aef-8906-b86ec0413163"; } 
                                 
                            }  
                            ref :>> ownedDeploymentLinks =  ('d69ee3bc-dd57-4aef-8906-b86ec0413163'); 
                             
                        }  
                        part '988f426a-0807-4466-a75f-0ddc09224fdf' : CPart :> 'Isolation Valve'  { 
                            @CapellaID { eid = "988f426a-0807-4466-a75f-0ddc09224fdf"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation 'e75c6dae-8a4e-4389-ab80-9b22b9c01b10' : PartDeploymentLink
                                allocate deployedElement ::> 'Behavior Parent'.'7351d56a-1d18-47d4-8545-7082891ecee8'
                                to location ::> 'Nose Landing Gear Library'::'Nose Landing Gear'::'Physical Architecture'::'Structure'::'Physical System'.'Braking Hydralulic Subsystem'.'988f426a-0807-4466-a75f-0ddc09224fdf' { 
                                @CapellaID { eid = "e75c6dae-8a4e-4389-ab80-9b22b9c01b10"; } 
                                 
                            }  
                            ref :>> ownedDeploymentLinks =  ('e75c6dae-8a4e-4389-ab80-9b22b9c01b10'); 
                             
                        }  
                        part '60880e20-0215-46d0-9804-22c0dd6ccf35' : CPart :> 'Shutoff Valve'  { 
                            @CapellaID { eid = "60880e20-0215-46d0-9804-22c0dd6ccf35"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation '70f9ccaa-8760-4914-a458-38a12b11c3ac' : PartDeploymentLink
                                allocate deployedElement ::> 'Behavior Parent'.'1b07bf32-e720-435e-b7f1-613b66e56098'
                                to location ::> 'Nose Landing Gear Library'::'Nose Landing Gear'::'Physical Architecture'::'Structure'::'Physical System'.'Braking Hydralulic Subsystem'.'60880e20-0215-46d0-9804-22c0dd6ccf35' { 
                                @CapellaID { eid = "70f9ccaa-8760-4914-a458-38a12b11c3ac"; } 
                                 
                            }  
                            ref :>> ownedDeploymentLinks =  ('70f9ccaa-8760-4914-a458-38a12b11c3ac'); 
                             
                        }  
                        part '69d98d35-92fe-4117-99ad-a315c75a0ac5' : CPart :> 'Selector Valve'  { 
                            @CapellaID { eid = "69d98d35-92fe-4117-99ad-a315c75a0ac5"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation '446b128d-90b5-4536-ac3e-71eaa2f6ace4' : PartDeploymentLink
                                allocate deployedElement ::> 'Behavior Parent'.'Fuel and Power System'.'ad74f09b-9131-4a78-ab84-ad42de46af1c'
                                to location ::> 'Nose Landing Gear Library'::'Nose Landing Gear'::'Physical Architecture'::'Structure'::'Physical System'.'Braking Hydralulic Subsystem'.'69d98d35-92fe-4117-99ad-a315c75a0ac5' { 
                                @CapellaID { eid = "446b128d-90b5-4536-ac3e-71eaa2f6ace4"; } 
                                 
                            }  
                            ref :>> ownedDeploymentLinks =  ('446b128d-90b5-4536-ac3e-71eaa2f6ace4'); 
                             
                        }  
                        part '5b2e2f43-fb96-4c25-808f-c70fc371a919' : CPart :> 'Accumulator '  { 
                            @CapellaID { eid = "5b2e2f43-fb96-4c25-808f-c70fc371a919"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation '5b40aedb-1b37-4740-b86a-e51b95f48c98' : PartDeploymentLink
                                allocate deployedElement ::> 'Behavior Parent'.'Fuel and Power System'.'00ce9c69-5878-4780-bc4e-868d34e6e706'
                                to location ::> 'Nose Landing Gear Library'::'Nose Landing Gear'::'Physical Architecture'::'Structure'::'Physical System'.'Braking Hydralulic Subsystem'.'5b2e2f43-fb96-4c25-808f-c70fc371a919' { 
                                @CapellaID { eid = "5b40aedb-1b37-4740-b86a-e51b95f48c98"; } 
                                 
                            }  
                            ref :>> ownedDeploymentLinks =  ('5b40aedb-1b37-4740-b86a-e51b95f48c98'); 
                             
                        }  
                        part 'a7585566-2fbe-474d-a9df-2cee153d7de8' : CPart :> 'Junction'  { 
                            @CapellaID { eid = "a7585566-2fbe-474d-a9df-2cee153d7de8"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation '209f9901-e2b3-4ec5-9c25-124f221b3c43' : PartDeploymentLink
                                allocate deployedElement ::> 'Behavior Parent'.'Fuel and Power System'.'5e39a677-77d9-4af8-a2b3-26824e320f34'
                                to location ::> 'Nose Landing Gear Library'::'Nose Landing Gear'::'Physical Architecture'::'Structure'::'Physical System'.'Braking Hydralulic Subsystem'.'a7585566-2fbe-474d-a9df-2cee153d7de8' { 
                                @CapellaID { eid = "209f9901-e2b3-4ec5-9c25-124f221b3c43"; } 
                                 
                            }  
                            ref :>> ownedDeploymentLinks =  ('209f9901-e2b3-4ec5-9c25-124f221b3c43'); 
                             
                        }  
                        interface '4331303b-d330-4393-83b9-21a050528ab7' : PhysicalLink 
                            connect sourcePhysicalPort ::> 'Green Hydraulic Pump'.'PP 2'
                            to targetPhysicalPort ::> 'Shutoff Valve'.'PP 2' {
                            @CapellaID { eid = "4331303b-d330-4393-83b9-21a050528ab7"; } 
                            attribute :>> interfaceName = "Pipe 11"; 
                             
                        }  
                        interface 'eb02e304-98ba-4ca2-8fa8-57937f6ecbc3' : PhysicalLink 
                            connect sourcePhysicalPort ::> 'Blue Hydraulic Pump'.'PP 2'
                            to targetPhysicalPort ::> 'Isolation Valve'.'PP 1' {
                            @CapellaID { eid = "eb02e304-98ba-4ca2-8fa8-57937f6ecbc3"; } 
                            attribute :>> interfaceName = "Pipe 9"; 
                             
                             
                        }  
                        interface '0f18661a-ad8c-4473-9d94-cd13c433ef9d' : PhysicalLink 
                            connect sourcePhysicalPort ::> 'Isolation Valve'.'PP 2'
                            to targetPhysicalPort ::> 'Selector Valve'.'PP 1' {
                            @CapellaID { eid = "0f18661a-ad8c-4473-9d94-cd13c433ef9d"; } 
                            attribute :>> interfaceName = "Pipe 10"; 
                             
                             
                        }  
                        interface 'fee8e2cb-7664-41b7-9dc1-84b79d1de25b' : PhysicalLink 
                            connect sourcePhysicalPort ::> 'Shutoff Valve'.'PP 3'
                            to targetPhysicalPort ::> 'Selector Valve'.'PP 3' {
                            @CapellaID { eid = "fee8e2cb-7664-41b7-9dc1-84b79d1de25b"; } 
                            attribute :>> interfaceName = "Pipe 12"; 
                             
                             
                        }  
                        part 'Blue Hydraulic Pump' : PhysicalComponent { 
                            @CapellaID { eid = "3c8b69de-deca-4b9e-8807-897df8371ab4"; } 
                            attribute :>> isAbstract = false; 
                            attribute :>> isActor = false; 
                            attribute :>> isHuman = false; 
                            attribute :>> kind = PhysicalComponentKind::UNSET; 
                            attribute :>> nature = PhysicalComponentNature::NODE; 
                            port 'Fluid In' : PhysicalPort { 
                                @CapellaID { eid = "d4575bab-b554-43df-a311-57ee5eeac7e6"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '2b98ec3c-f809-48d0-b678-26452362f86f' : ComponentPortAllocation
                                    allocate allocatedPort ::> 'Fluid In'
                                    to allocatingPort ::> 'Nose Landing Gear Library'::'Nose Landing Gear'::'Physical Architecture'::'Structure'::'Physical System'.'Behavior Parent'.'Blue Hydraulic Pump'.'CP 1' { 
                                    @CapellaID { eid = "2b98ec3c-f809-48d0-b678-26452362f86f"; } 
                                     
                                }  
                                 
                                ref :>> ownedComponentPortAllocations =  ('2b98ec3c-f809-48d0-b678-26452362f86f'); 
                            }  
                            port 'PP 2' : PhysicalPort { 
                                @CapellaID { eid = "2c280538-60f9-4dd4-9da2-3472f22a1638"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '856c22fe-435a-44b3-b4ef-20d1a04b964a' : ComponentPortAllocation
                                    allocate allocatedPort ::> 'PP 2'
                                    to allocatingPort ::> 'Nose Landing Gear Library'::'Nose Landing Gear'::'Physical Architecture'::'Structure'::'Physical System'.'Behavior Parent'.'Blue Hydraulic Pump'.'CP 2' { 
                                    @CapellaID { eid = "856c22fe-435a-44b3-b4ef-20d1a04b964a"; } 
                                     
                                }  
                                 
                                ref :>> ownedComponentPortAllocations =  ('856c22fe-435a-44b3-b4ef-20d1a04b964a'); 
                            }  
                            attribute 'Hydraulic Pump' : PropertyValueGroup { 
                                @CapellaID { eid = "862e8954-a421-4ac7-b7ce-cfd1a189cf97"; } 
                                attribute 'Max Pressure (PSI)' : FloatPropertyValue  = 100.0 { 
                                    @CapellaID { eid = "12968dbe-d9af-43d8-a01a-f26381437073"; } 
                                }  
                                attribute 'FloatPropertyValue 2' : FloatPropertyValue  = 0.0 { 
                                    @CapellaID { eid = "d27e1093-eb13-4f22-a83b-bff5f48c34b1"; } 
                                }  
                                ref :>> ownedPropertyValues =  ('Max Pressure (PSI)',
                                'FloatPropertyValue 2'); 
                            }  
                            ref :>> appliedPropertyValueGroups =  ('Hydraulic Pump'); 
                             
                            ref :>> ownedPropertyValueGroups =  ('Hydraulic Pump'); 
                        }  
                        part 'Green Hydraulic Pump' : PhysicalComponent { 
                            @CapellaID { eid = "7000f7b4-4765-41dd-8cd9-9cc86187f713"; } 
                            attribute :>> isAbstract = false; 
                            attribute :>> isActor = false; 
                            attribute :>> isHuman = false; 
                            attribute :>> kind = PhysicalComponentKind::UNSET; 
                            attribute :>> nature = PhysicalComponentNature::NODE; 
                            port 'Fluid In' : PhysicalPort { 
                                @CapellaID { eid = "81a82f7e-9123-4abe-9542-070f12d38d76"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '116cb264-98d6-4c37-9b87-acabdd40d9e2' : ComponentPortAllocation
                                    allocate allocatedPort ::> 'Fluid In'
                                    to allocatingPort ::> 'Nose Landing Gear Library'::'Nose Landing Gear'::'Physical Architecture'::'Structure'::'Physical System'.'Behavior Parent'.'Fuel and Power System'.'Green Hydaulic Pump'.'CP 1' { 
                                    @CapellaID { eid = "116cb264-98d6-4c37-9b87-acabdd40d9e2"; } 
                                     
                                }  
                                 
                                ref :>> ownedComponentPortAllocations =  ('116cb264-98d6-4c37-9b87-acabdd40d9e2'); 
                            }  
                            port 'PP 2' : PhysicalPort { 
                                @CapellaID { eid = "0263e6e6-ff03-4ea3-8ea1-3b44819d439e"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            attribute 'PropertyValueGroup 1' : PropertyValueGroup { 
                                @CapellaID { eid = "61dbdaab-2460-48f1-8060-acd61b06c74f"; } 
                            }  
                            ref :>> appliedPropertyValueGroups =  ('PropertyValueGroup 1'); 
                             
                            ref :>> ownedPropertyValueGroups =  ('PropertyValueGroup 1'); 
                        }  
                        part 'Isolation Valve' : PhysicalComponent { 
                            @CapellaID { eid = "2ba8cbd2-3715-4863-876a-c9ba079e0061"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "d2c08364-816c-4ba8-98fb-8a2f5d5e8668"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '18e617c0-c7d5-454f-b845-d2c08107ca73' : ComponentPortAllocation
                                    allocate allocatedPort ::> 'PP 1'
                                    to allocatingPort ::> 'Nose Landing Gear Library'::'Nose Landing Gear'::'Physical Architecture'::'Structure'::'Physical System'.'Behavior Parent'.'Isolation Valve'.'CP 1' { 
                                    @CapellaID { eid = "18e617c0-c7d5-454f-b845-d2c08107ca73"; } 
                                     
                                }  
                                 
                                ref :>> ownedComponentPortAllocations =  ('18e617c0-c7d5-454f-b845-d2c08107ca73'); 
                            }  
                            port 'PP 2' : PhysicalPort { 
                                @CapellaID { eid = "3bd2ebed-a642-418c-90e6-63097604080c"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '18c9c9d9-43ea-457d-a734-9521a5d4a9a6' : ComponentPortAllocation
                                    allocate allocatedPort ::> 'PP 2'
                                    to allocatingPort ::> 'Nose Landing Gear Library'::'Nose Landing Gear'::'Physical Architecture'::'Structure'::'Physical System'.'Behavior Parent'.'Isolation Valve'.'CP 2' { 
                                    @CapellaID { eid = "18c9c9d9-43ea-457d-a734-9521a5d4a9a6"; } 
                                     
                                }  
                                 
                                ref :>> ownedComponentPortAllocations =  ('18c9c9d9-43ea-457d-a734-9521a5d4a9a6'); 
                            }  
                            port 'PP 3' : PhysicalPort { 
                                @CapellaID { eid = "a68ae810-c5b6-4425-b539-24b8237a9652"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                             
                        }  
                        part 'Shutoff Valve' : PhysicalComponent { 
                            @CapellaID { eid = "e0b66c6e-e316-4369-8fde-a19d4faebc74"; } 
                            attribute :>> isAbstract = false; 
                            attribute :>> isActor = false; 
                            attribute :>> isHuman = false; 
                            attribute :>> kind = PhysicalComponentKind::UNSET; 
                            attribute :>> nature = PhysicalComponentNature::NODE; 
                            port 'Control In' : PhysicalPort { 
                                @CapellaID { eid = "efd3878d-1522-4ade-9f8d-93460f8c082d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 2' : PhysicalPort { 
                                @CapellaID { eid = "fa9ded38-12a8-428a-a1a6-7dfc3e1d2ffa"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 3' : PhysicalPort { 
                                @CapellaID { eid = "901b5899-43d7-4974-bf14-975cc587897e"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '62e62987-cada-4815-90cc-bda38167a719' : ComponentPortAllocation
                                    allocate allocatedPort ::> 'PP 3'
                                    to allocatingPort ::> 'Nose Landing Gear Library'::'Nose Landing Gear'::'Physical Architecture'::'Structure'::'Physical System'.'Behavior Parent'.'Shutoff Valve'.'CP 2' { 
                                    @CapellaID { eid = "62e62987-cada-4815-90cc-bda38167a719"; } 
                                     
                                }  
                                 
                                ref :>> ownedComponentPortAllocations =  ('62e62987-cada-4815-90cc-bda38167a719'); 
                            }  
                             
                        }  
                        part 'Selector Valve' : PhysicalComponent { 
                            @CapellaID { eid = "056a7613-1a33-4ee4-a29c-5b397ffe24be"; } 
                            attribute :>> isAbstract = false; 
                            attribute :>> isActor = false; 
                            attribute :>> isHuman = false; 
                            attribute :>> kind = PhysicalComponentKind::UNSET; 
                            attribute :>> nature = PhysicalComponentNature::NODE; 
                            port 'PP 2' : PhysicalPort { 
                                @CapellaID { eid = "f0fb4673-7ca1-462d-8d98-8de7ce762dda"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '0b7677d6-9396-4608-87a4-689b381b42bf' : ComponentPortAllocation
                                    allocate allocatedPort ::> 'PP 2'
                                    to allocatingPort ::> 'Nose Landing Gear Library'::'Nose Landing Gear'::'Physical Architecture'::'Structure'::'Physical System'.'Behavior Parent'.'Fuel and Power System'.'Selector Valve'.'CP 3' { 
                                    @CapellaID { eid = "0b7677d6-9396-4608-87a4-689b381b42bf"; } 
                                     
                                }  
                                 
                                ref :>> ownedComponentPortAllocations =  ('0b7677d6-9396-4608-87a4-689b381b42bf'); 
                            }  
                            port 'PP 1' : PhysicalPort { 
                                @CapellaID { eid = "d858c8bc-2458-43e8-88be-dabaf8a51eac"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation 'cc74be3c-67b2-42cc-a4ac-19a304df84c3' : ComponentPortAllocation
                                    allocate allocatedPort ::> 'PP 1'
                                    to allocatingPort ::> 'Nose Landing Gear Library'::'Nose Landing Gear'::'Physical Architecture'::'Structure'::'Physical System'.'Behavior Parent'.'Fuel and Power System'.'Selector Valve'.'CP 1' { 
                                    @CapellaID { eid = "cc74be3c-67b2-42cc-a4ac-19a304df84c3"; } 
                                     
                                }  
                                 
                                ref :>> ownedComponentPortAllocations =  ('cc74be3c-67b2-42cc-a4ac-19a304df84c3'); 
                            }  
                            port 'PP 3' : PhysicalPort { 
                                @CapellaID { eid = "236843a3-94ed-4859-81e8-4305bd95fd93"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '05d16030-a370-4575-b3aa-64e85557e18a' : ComponentPortAllocation
                                    allocate allocatedPort ::> 'PP 3'
                                    to allocatingPort ::> 'Nose Landing Gear Library'::'Nose Landing Gear'::'Physical Architecture'::'Structure'::'Physical System'.'Behavior Parent'.'Fuel and Power System'.'Selector Valve'.'CP 2' { 
                                    @CapellaID { eid = "05d16030-a370-4575-b3aa-64e85557e18a"; } 
                                     
                                }  
                                 
                                ref :>> ownedComponentPortAllocations =  ('05d16030-a370-4575-b3aa-64e85557e18a'); 
                            }  
                             
                        }  
                        part 'Accumulator ' : PhysicalComponent { 
                            @CapellaID { eid = "70663da0-1ada-4594-b6ee-ea04ddb70e9b"; } 
                            attribute :>> isAbstract = false; 
                            attribute :>> isActor = false; 
                            attribute :>> isHuman = false; 
                            attribute :>> kind = PhysicalComponentKind::UNSET; 
                            attribute :>> nature = PhysicalComponentNature::NODE; 
                            port 'PP 2' : PhysicalPort { 
                                @CapellaID { eid = "02430440-f9ec-4993-931a-14c4edc669ea"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                             
                        }  
                        part 'Junction' : PhysicalComponent { 
                            @CapellaID { eid = "52a97b81-841b-491c-8c7c-82a8f60ecce8"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "b7e2d361-ea4e-4078-80eb-c917c355ac5a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation 'e77a46cc-4eea-49b4-af90-52dc248d0156' : ComponentPortAllocation
                                    allocate allocatedPort ::> 'PP 1'
                                    to allocatingPort ::> 'Nose Landing Gear Library'::'Nose Landing Gear'::'Physical Architecture'::'Structure'::'Physical System'.'Behavior Parent'.'Fuel and Power System'.'Junction'.'CP 1' { 
                                    @CapellaID { eid = "e77a46cc-4eea-49b4-af90-52dc248d0156"; } 
                                     
                                }  
                                 
                                ref :>> ownedComponentPortAllocations =  ('e77a46cc-4eea-49b4-af90-52dc248d0156'); 
                            }  
                            port 'PP 2' : PhysicalPort { 
                                @CapellaID { eid = "0fc12552-a230-49e6-983d-7ec7ea0215e2"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'Geatr Out' : PhysicalPort { 
                                @CapellaID { eid = "cc544401-f977-4528-bec2-65bfc97474f4"; sid = "cc544401-f977-4528-bec2-65bfc97474f4"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '5dc430b0-f71e-45f6-b2e0-112270cab338' : ComponentPortAllocation
                                    allocate allocatedPort ::> 'Geatr Out'
                                    to allocatingPort ::> 'Nose Landing Gear Library'::'Nose Landing Gear'::'Physical Architecture'::'Structure'::'Physical System'.'Behavior Parent'.'Fuel and Power System'.'Junction'.'CP 2' { 
                                    @CapellaID { eid = "5dc430b0-f71e-45f6-b2e0-112270cab338"; } 
                                     
                                }  
                                 
                                ref :>> ownedComponentPortAllocations =  ('5dc430b0-f71e-45f6-b2e0-112270cab338'); 
                            }  
                             
                        }  
                        ref :>> ownedPhysicalLinks =  ('4331303b-d330-4393-83b9-21a050528ab7',
                        'eb02e304-98ba-4ca2-8fa8-57937f6ecbc3',
                        '0f18661a-ad8c-4473-9d94-cd13c433ef9d',
                        'fee8e2cb-7664-41b7-9dc1-84b79d1de25b'); 
                         
                        ref :>> ownedPhysicalComponents =  ('Blue Hydraulic Pump',
                        'Green Hydraulic Pump',
                        'Isolation Valve',
                        'Shutoff Valve',
                        'Selector Valve',
                        'Accumulator ',
                        'Junction'); 
                    }  
                    part 'Hydraulic ' : PhysicalComponent { 
                        @CapellaID { eid = "928e9dcb-7d67-47c9-90ec-ad612d40fee0"; sid = "928e9dcb-7d67-47c9-90ec-ad612d40fee0"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "01de47e1-a1b8-4e67-851c-4ad1534553af"; sid = "01de47e1-a1b8-4e67-851c-4ad1534553af"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '414cdb4a-f8c1-48e7-9f46-d5efbe05b860' : ComponentPortAllocation
                                allocate allocatedPort ::> 'PP 1'
                                to allocatingPort ::> 'Nose Landing Gear Library'::'Nose Landing Gear'::'Physical Architecture'::'Structure'::'Physical System'.'Behavior Parent'.'Pressured Hydraulic'.'CP 2' { 
                                @CapellaID { eid = "414cdb4a-f8c1-48e7-9f46-d5efbe05b860"; } 
                                 
                            }  
                            ref allocation 'cb69330c-0b26-427a-bcce-9aad38931ef6' : ComponentPortAllocation
                                allocate allocatedPort ::> 'PP 1'
                                to allocatingPort ::> 'Nose Landing Gear Library'::'Nose Landing Gear'::'Physical Architecture'::'Structure'::'Physical System'.'Behavior Parent'.'Pressured Hydraulic'.'CP 3' { 
                                @CapellaID { eid = "cb69330c-0b26-427a-bcce-9aad38931ef6"; } 
                                 
                            }  
                             
                            ref :>> ownedComponentPortAllocations =  ('414cdb4a-f8c1-48e7-9f46-d5efbe05b860',
                            'cb69330c-0b26-427a-bcce-9aad38931ef6'); 
                        }  
                        port 'PP 2' : PhysicalPort { 
                            @CapellaID { eid = "4a63708f-897d-4d91-81cc-3f05d788021b"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation 'c6a60f9f-bebf-454b-8569-f628d83a6d61' : ComponentPortAllocation
                                allocate allocatedPort ::> 'PP 2'
                                to allocatingPort ::> 'Nose Landing Gear Library'::'Nose Landing Gear'::'Physical Architecture'::'Structure'::'Physical System'.'Behavior Parent'.'Pressured Hydraulic'.'CP 1' { 
                                @CapellaID { eid = "c6a60f9f-bebf-454b-8569-f628d83a6d61"; } 
                                 
                            }  
                             
                            ref :>> ownedComponentPortAllocations =  ('c6a60f9f-bebf-454b-8569-f628d83a6d61'); 
                        }  
                         
                    }  
                    part 'Airframe' : PhysicalComponent { 
                        @CapellaID { eid = "7868e736-abd9-4005-8a5a-57ecf508d0e9"; sid = "7868e736-abd9-4005-8a5a-57ecf508d0e9"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "a62b322e-26d0-478b-8e8a-d53d1b97c351"; sid = "a62b322e-26d0-478b-8e8a-d53d1b97c351"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '261829c5-0e5c-4b1f-9e24-a4f965f4d01f' : ComponentPortAllocation
                                allocate allocatedPort ::> 'PP 1'
                                to allocatingPort ::> 'Nose Landing Gear Library'::'Nose Landing Gear'::'Physical Architecture'::'Structure'::'Physical System'.'Behavior Parent'.'Airframe'.'CP 5' { 
                                @CapellaID { eid = "261829c5-0e5c-4b1f-9e24-a4f965f4d01f"; } 
                                 
                            }  
                             
                            ref :>> ownedComponentPortAllocations =  ('261829c5-0e5c-4b1f-9e24-a4f965f4d01f'); 
                        }  
                        port 'PP 2' : PhysicalPort { 
                            @CapellaID { eid = "ecf391a6-fff6-4c71-84e2-ea8e2ea9d3f0"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation 'e2db6492-2ecd-4e1b-b19b-a1421874105d' : ComponentPortAllocation
                                allocate allocatedPort ::> 'PP 2'
                                to allocatingPort ::> 'Nose Landing Gear Library'::'Nose Landing Gear'::'Physical Architecture'::'Structure'::'Physical System'.'Behavior Parent'.'Airframe'.'CP 4' { 
                                @CapellaID { eid = "e2db6492-2ecd-4e1b-b19b-a1421874105d"; } 
                                 
                            }  
                             
                            ref :>> ownedComponentPortAllocations =  ('e2db6492-2ecd-4e1b-b19b-a1421874105d'); 
                        }  
                         
                    }  
                    part 'Data Bus 1' : PhysicalComponent { 
                        @CapellaID { eid = "bf62392b-6c78-4887-b31f-065604c5e188"; sid = "bf62392b-6c78-4887-b31f-065604c5e188"; } 
                        attribute :>> isAbstract = false; 
                        attribute :>> isActor = false; 
                        attribute :>> isHuman = false; 
                        attribute :>> kind = PhysicalComponentKind::UNSET; 
                        attribute :>> nature = PhysicalComponentNature::NODE; 
                         
                    }  
                    part 'Bus 1' : PhysicalComponent { 
                        @CapellaID { eid = "4f8fbe66-b367-44f9-b33a-92d4c4bcd354"; sid = "4f8fbe66-b367-44f9-b33a-92d4c4bcd354"; } 
                        attribute :>> isAbstract = false; 
                        attribute :>> isActor = false; 
                        attribute :>> isHuman = false; 
                        attribute :>> kind = PhysicalComponentKind::UNSET; 
                        attribute :>> nature = PhysicalComponentNature::NODE; 
                         
                    }  
                    part 'LGL Harness' : PhysicalComponent { 
                        @CapellaID { eid = "9a0669ac-ad81-4b85-96c8-6342915bb091"; sid = "9a0669ac-ad81-4b85-96c8-6342915bb091"; } 
                        attribute :>> isAbstract = false; 
                        attribute :>> isActor = false; 
                        attribute :>> isHuman = false; 
                        attribute :>> kind = PhysicalComponentKind::UNSET; 
                        attribute :>> nature = PhysicalComponentNature::NODE; 
                         
                    }  
                    part 'Nose Landing Gear' : PhysicalComponent { 
                        @CapellaID { eid = "65b36979-e5d2-471e-b3a5-d2875cbe66b9"; } 
                        attribute :>> isAbstract = false; 
                        attribute :>> isActor = false; 
                        attribute :>> isHuman = false; 
                        attribute :>> kind = PhysicalComponentKind::UNSET; 
                        attribute :>> nature = PhysicalComponentNature::NODE; 
                        part '0e9092d4-488c-4a08-9c8b-1bd65fe687ea' : CPart :> 'NLG Door Sensor'  { 
                            @CapellaID { eid = "0e9092d4-488c-4a08-9c8b-1bd65fe687ea"; sid = "0e9092d4-488c-4a08-9c8b-1bd65fe687ea"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation 'fe31e97c-92a6-4350-b717-20617f3e6b5f' : PartDeploymentLink
                                allocate deployedElement ::> 'Behavior Parent'.'964d5412-c1e7-43cd-8e48-9dc72148801b'
                                to location ::> 'Nose Landing Gear Library'::'Nose Landing Gear'::'Physical Architecture'::'Structure'::'Physical System'.'Nose Landing Gear'.'0e9092d4-488c-4a08-9c8b-1bd65fe687ea' { 
                                @CapellaID { eid = "fe31e97c-92a6-4350-b717-20617f3e6b5f"; } 
                                 
                            }  
                            ref :>> ownedDeploymentLinks =  ('fe31e97c-92a6-4350-b717-20617f3e6b5f'); 
                             
                        }  
                        part '41ec89e1-5839-4e28-8138-e40740c59e91' : CPart :> 'NLG Uplock Sensor 1'  { 
                            @CapellaID { eid = "41ec89e1-5839-4e28-8138-e40740c59e91"; sid = "41ec89e1-5839-4e28-8138-e40740c59e91"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation '377df7ae-b825-47ff-9cf1-562edfa61698' : PartDeploymentLink
                                allocate deployedElement ::> 'Behavior Parent'.'d4d60991-ba83-4b37-a894-6c1299572d0a'
                                to location ::> 'Nose Landing Gear Library'::'Nose Landing Gear'::'Physical Architecture'::'Structure'::'Physical System'.'Nose Landing Gear'.'41ec89e1-5839-4e28-8138-e40740c59e91' { 
                                @CapellaID { eid = "377df7ae-b825-47ff-9cf1-562edfa61698"; } 
                                 
                            }  
                            ref :>> ownedDeploymentLinks =  ('377df7ae-b825-47ff-9cf1-562edfa61698'); 
                             
                        }  
                        part '0e4ba20c-86ad-4cec-a0c2-b3b2adfc825e' : CPart :> 'Landing Gear Control and Indication Computer'  { 
                            @CapellaID { eid = "0e4ba20c-86ad-4cec-a0c2-b3b2adfc825e"; sid = "0e4ba20c-86ad-4cec-a0c2-b3b2adfc825e"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation 'fa8788bf-e803-4210-bfd5-cf4ee22d6c44' : PartDeploymentLink
                                allocate deployedElement ::> 'Landing Gear Control and Indication Computer'.'eb7da3b1-ba85-4a01-b68f-2f17b0c9549e'
                                to location ::> 'Nose Landing Gear Library'::'Nose Landing Gear'::'Physical Architecture'::'Structure'::'Physical System'.'Nose Landing Gear'.'0e4ba20c-86ad-4cec-a0c2-b3b2adfc825e' { 
                                @CapellaID { eid = "fa8788bf-e803-4210-bfd5-cf4ee22d6c44"; } 
                                 
                            }  
                            allocation '6c4a6163-664c-483b-82a4-0549a8324da8' : PartDeploymentLink
                                allocate deployedElement ::> 'Behavior Parent'.'Fuel and Power System'.'cf6df715-4cd6-41a8-9a24-c293c242811f'
                                to location ::> 'Nose Landing Gear Library'::'Nose Landing Gear'::'Physical Architecture'::'Structure'::'Physical System'.'Nose Landing Gear'.'0e4ba20c-86ad-4cec-a0c2-b3b2adfc825e' { 
                                @CapellaID { eid = "6c4a6163-664c-483b-82a4-0549a8324da8"; } 
                                 
                            }  
                            ref :>> ownedDeploymentLinks =  ('fa8788bf-e803-4210-bfd5-cf4ee22d6c44',
                            '6c4a6163-664c-483b-82a4-0549a8324da8'); 
                             
                        }  
                        part '5815d643-420a-4db2-8a65-a78f8fb5f063' : CPart :> 'NLG Downlock Sensor 2'  { 
                            @CapellaID { eid = "5815d643-420a-4db2-8a65-a78f8fb5f063"; sid = "5815d643-420a-4db2-8a65-a78f8fb5f063"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation 'a032c21f-4e9f-4d02-be3a-67788f2bba4a' : PartDeploymentLink
                                allocate deployedElement ::> 'Behavior Parent'.'2c5933bc-4f77-4bd2-830f-ef8a4b15ab79'
                                to location ::> 'Nose Landing Gear Library'::'Nose Landing Gear'::'Physical Architecture'::'Structure'::'Physical System'.'Nose Landing Gear'.'5815d643-420a-4db2-8a65-a78f8fb5f063' { 
                                @CapellaID { eid = "a032c21f-4e9f-4d02-be3a-67788f2bba4a"; } 
                                 
                            }  
                            ref :>> ownedDeploymentLinks =  ('a032c21f-4e9f-4d02-be3a-67788f2bba4a'); 
                             
                        }  
                        part 'd9646e1e-1c89-4def-b2b9-11b708506d6f' : CPart :> 'NLG Uplock Sensor 2'  { 
                            @CapellaID { eid = "d9646e1e-1c89-4def-b2b9-11b708506d6f"; sid = "d9646e1e-1c89-4def-b2b9-11b708506d6f"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation '47a3f0dc-b08b-4a1b-91d0-6afe323a8c4c' : PartDeploymentLink
                                allocate deployedElement ::> 'Behavior Parent'.'ece32dd0-24f7-461d-aaa6-37c034d46293'
                                to location ::> 'Nose Landing Gear Library'::'Nose Landing Gear'::'Physical Architecture'::'Structure'::'Physical System'.'Nose Landing Gear'.'d9646e1e-1c89-4def-b2b9-11b708506d6f' { 
                                @CapellaID { eid = "47a3f0dc-b08b-4a1b-91d0-6afe323a8c4c"; } 
                                 
                            }  
                            ref :>> ownedDeploymentLinks =  ('47a3f0dc-b08b-4a1b-91d0-6afe323a8c4c'); 
                             
                        }  
                        part '5de997f1-c0c3-4ec4-834b-2a2c11db80a9' : CPart :> 'NLG Structural Post Assembly'  { 
                            @CapellaID { eid = "5de997f1-c0c3-4ec4-834b-2a2c11db80a9"; sid = "5de997f1-c0c3-4ec4-834b-2a2c11db80a9"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation '6d4c48ea-c6ba-463e-990c-424dc69d5e53' : PartDeploymentLink
                                allocate deployedElement ::> 'Behavior Parent'.'bf33130a-0fb5-476b-90fe-009b09618fdf'
                                to location ::> 'Nose Landing Gear Library'::'Nose Landing Gear'::'Physical Architecture'::'Structure'::'Physical System'.'Nose Landing Gear'.'5de997f1-c0c3-4ec4-834b-2a2c11db80a9' { 
                                @CapellaID { eid = "6d4c48ea-c6ba-463e-990c-424dc69d5e53"; } 
                                 
                            }  
                            ref :>> ownedDeploymentLinks =  ('6d4c48ea-c6ba-463e-990c-424dc69d5e53'); 
                             
                        }  
                        part 'd253edde-948c-418d-a0b8-60b14e0f17a3' : CPart :> 'Weight on Wheel Sensor 2'  { 
                            @CapellaID { eid = "d253edde-948c-418d-a0b8-60b14e0f17a3"; sid = "d253edde-948c-418d-a0b8-60b14e0f17a3"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation '18ff96f3-a373-4f4b-b58a-925fad0d1298' : PartDeploymentLink
                                allocate deployedElement ::> 'Behavior Parent'.'75cb0d7a-cebb-4b7e-8a82-79d68ac11430'
                                to location ::> 'Nose Landing Gear Library'::'Nose Landing Gear'::'Physical Architecture'::'Structure'::'Physical System'.'Nose Landing Gear'.'d253edde-948c-418d-a0b8-60b14e0f17a3' { 
                                @CapellaID { eid = "18ff96f3-a373-4f4b-b58a-925fad0d1298"; } 
                                 
                            }  
                            ref :>> ownedDeploymentLinks =  ('18ff96f3-a373-4f4b-b58a-925fad0d1298'); 
                             
                        }  
                        part '84ef3892-0f13-474e-b0b6-da0d200520af' : CPart :> 'NLG Wheel Housing and Assembly'  { 
                            @CapellaID { eid = "84ef3892-0f13-474e-b0b6-da0d200520af"; sid = "84ef3892-0f13-474e-b0b6-da0d200520af"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation 'c0598c6b-44d9-4ff7-a3ff-7eeb0445bd96' : PartDeploymentLink
                                allocate deployedElement ::> 'Behavior Parent'.'749bbb13-35c4-45d4-a813-c3e0536fd141'
                                to location ::> 'Nose Landing Gear Library'::'Nose Landing Gear'::'Physical Architecture'::'Structure'::'Physical System'.'Nose Landing Gear'.'84ef3892-0f13-474e-b0b6-da0d200520af' { 
                                @CapellaID { eid = "c0598c6b-44d9-4ff7-a3ff-7eeb0445bd96"; } 
                                 
                            }  
                            ref :>> ownedDeploymentLinks =  ('c0598c6b-44d9-4ff7-a3ff-7eeb0445bd96'); 
                             
                        }  
                        part '016aa95f-e40e-48c2-82ec-7fc6c028dbdb' : CPart :> 'NLG Shock Absorber'  { 
                            @CapellaID { eid = "016aa95f-e40e-48c2-82ec-7fc6c028dbdb"; sid = "016aa95f-e40e-48c2-82ec-7fc6c028dbdb"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation '6a986936-ee95-41b6-9de6-d9bc5e7f412f' : PartDeploymentLink
                                allocate deployedElement ::> 'Behavior Parent'.'b8f45b4b-30d6-4f43-be5f-6a3777f05763'
                                to location ::> 'Nose Landing Gear Library'::'Nose Landing Gear'::'Physical Architecture'::'Structure'::'Physical System'.'Nose Landing Gear'.'016aa95f-e40e-48c2-82ec-7fc6c028dbdb' { 
                                @CapellaID { eid = "6a986936-ee95-41b6-9de6-d9bc5e7f412f"; } 
                                 
                            }  
                            ref :>> ownedDeploymentLinks =  ('6a986936-ee95-41b6-9de6-d9bc5e7f412f'); 
                             
                        }  
                        part '76f02759-5336-4ac2-a3f7-4eeb8aae324f' : CPart :> 'Weight on Wheel Sensor 1'  { 
                            @CapellaID { eid = "76f02759-5336-4ac2-a3f7-4eeb8aae324f"; sid = "76f02759-5336-4ac2-a3f7-4eeb8aae324f"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation 'e305d1ee-d76d-456c-9921-385b8d81a26d' : PartDeploymentLink
                                allocate deployedElement ::> 'Behavior Parent'.'64e734de-28ee-410a-a736-4b8fe959847e'
                                to location ::> 'Nose Landing Gear Library'::'Nose Landing Gear'::'Physical Architecture'::'Structure'::'Physical System'.'Nose Landing Gear'.'76f02759-5336-4ac2-a3f7-4eeb8aae324f' { 
                                @CapellaID { eid = "e305d1ee-d76d-456c-9921-385b8d81a26d"; } 
                                 
                            }  
                            ref :>> ownedDeploymentLinks =  ('e305d1ee-d76d-456c-9921-385b8d81a26d'); 
                             
                        }  
                        part 'deea7ca4-59b0-4b0c-b893-0d23c32a8f08' : CPart :> 'NLG Doors Dump Valve'  { 
                            @CapellaID { eid = "deea7ca4-59b0-4b0c-b893-0d23c32a8f08"; sid = "deea7ca4-59b0-4b0c-b893-0d23c32a8f08"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation '7f8fce9c-9b1b-464d-b3fa-99850c4d7384' : PartDeploymentLink
                                allocate deployedElement ::> 'Behavior Parent'.'e1acfc99-c49f-4f2a-8688-38c5f4fe8d8a'
                                to location ::> 'Nose Landing Gear Library'::'Nose Landing Gear'::'Physical Architecture'::'Structure'::'Physical System'.'Nose Landing Gear'.'deea7ca4-59b0-4b0c-b893-0d23c32a8f08' { 
                                @CapellaID { eid = "7f8fce9c-9b1b-464d-b3fa-99850c4d7384"; } 
                                 
                            }  
                            ref :>> ownedDeploymentLinks =  ('7f8fce9c-9b1b-464d-b3fa-99850c4d7384'); 
                             
                        }  
                        part '7aaf52dd-a94f-42c7-a5a9-548fa7ed02d9' : CPart :> 'NLG  Actuator'  { 
                            @CapellaID { eid = "7aaf52dd-a94f-42c7-a5a9-548fa7ed02d9"; sid = "7aaf52dd-a94f-42c7-a5a9-548fa7ed02d9"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation '8a3c5d77-5e25-4c8e-a3de-ba1aabffd671' : PartDeploymentLink
                                allocate deployedElement ::> 'Behavior Parent'.'cd969767-4080-46b2-9b0b-35ad6fa4b92d'
                                to location ::> 'Nose Landing Gear Library'::'Nose Landing Gear'::'Physical Architecture'::'Structure'::'Physical System'.'Nose Landing Gear'.'7aaf52dd-a94f-42c7-a5a9-548fa7ed02d9' { 
                                @CapellaID { eid = "8a3c5d77-5e25-4c8e-a3de-ba1aabffd671"; } 
                                 
                            }  
                            ref :>> ownedDeploymentLinks =  ('8a3c5d77-5e25-4c8e-a3de-ba1aabffd671'); 
                             
                        }  
                        part '677a4dd0-cf55-42b4-a7cf-c71f45437e29' : CPart :> 'NLG Door Actuator'  { 
                            @CapellaID { eid = "677a4dd0-cf55-42b4-a7cf-c71f45437e29"; sid = "677a4dd0-cf55-42b4-a7cf-c71f45437e29"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation '510b2b7e-a0e0-4e31-8591-6108780ca74b' : PartDeploymentLink
                                allocate deployedElement ::> 'Behavior Parent'.'40d3799b-932a-437e-aa46-9a6602e38fa9'
                                to location ::> 'Nose Landing Gear Library'::'Nose Landing Gear'::'Physical Architecture'::'Structure'::'Physical System'.'Nose Landing Gear'.'677a4dd0-cf55-42b4-a7cf-c71f45437e29' { 
                                @CapellaID { eid = "510b2b7e-a0e0-4e31-8591-6108780ca74b"; } 
                                 
                            }  
                            ref :>> ownedDeploymentLinks =  ('510b2b7e-a0e0-4e31-8591-6108780ca74b'); 
                             
                        }  
                        part '14634691-541f-462a-8143-87419ba13a06' : CPart :> 'NLG Door Selector Valve'  { 
                            @CapellaID { eid = "14634691-541f-462a-8143-87419ba13a06"; sid = "14634691-541f-462a-8143-87419ba13a06"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            allocation 'ad73e09b-855f-44dc-9b01-b976d91035e9' : PartDeploymentLink
                                allocate deployedElement ::> 'Behavior Parent'.'5c405984-5543-4f5a-ae8f-5761417aa328'
                                to location ::> 'Nose Landing Gear Library'::'Nose Landing Gear'::'Physical Architecture'::'Structure'::'Physical System'.'Nose Landing Gear'.'14634691-541f-462a-8143-87419ba13a06' { 
                                @CapellaID { eid = "ad73e09b-855f-44dc-9b01-b976d91035e9"; } 
                                 
                            }  
                            ref :>> ownedDeploymentLinks =  ('ad73e09b-855f-44dc-9b01-b976d91035e9'); 
                             
                        }  
                        interface '2bf670a3-1ba2-4182-9dad-471d5689b95e' : PhysicalLink 
                            connect sourcePhysicalPort ::> 'NLG Shock Absorber'.'PP 4'
                            to targetPhysicalPort ::> 'NLG Structural Post Assembly'.'PP 5' {
                            @CapellaID { eid = "2bf670a3-1ba2-4182-9dad-471d5689b95e"; } 
                            attribute :>> interfaceName = "Shock Absorber to Structural Post"; 
                             
                             
                        }  
                        interface '8c140267-99e2-4152-ae9c-967ed595e955' : PhysicalLink 
                            connect sourcePhysicalPort ::> 'NLG Wheel Housing and Assembly'.'PP 8'
                            to targetPhysicalPort ::> 'NLG Downlock Sensor 2'.'PP 1' {
                            @CapellaID { eid = "8c140267-99e2-4152-ae9c-967ed595e955"; sid = "8c140267-99e2-4152-ae9c-967ed595e955"; } 
                            attribute :>> interfaceName = "Wheel Housing to Downlock Sensor 2"; 
                             
                        }  
                        interface '7a1be218-3fb5-47d1-adea-529032a8b5ec' : PhysicalLink 
                            connect sourcePhysicalPort ::> 'NLG Wheel Housing and Assembly'.'PP 6'
                            to targetPhysicalPort ::> 'NLG Uplock Sensor 1'.'NLG Downlock Sensor 1'.'PP 1' {
                            @CapellaID { eid = "7a1be218-3fb5-47d1-adea-529032a8b5ec"; sid = "7a1be218-3fb5-47d1-adea-529032a8b5ec"; } 
                            attribute :>> interfaceName = "Wheel Housing to Downlock Sensor 1"; 
                             
                        }  
                        interface 'e0fdb2b6-f6b5-4d3a-808a-6d55ff5328c7' : PhysicalLink 
                            connect sourcePhysicalPort ::> 'NLG Wheel Housing and Assembly'.'PP 9'
                            to targetPhysicalPort ::> 'NLG Uplock Sensor 2'.'PP 1' {
                            @CapellaID { eid = "e0fdb2b6-f6b5-4d3a-808a-6d55ff5328c7"; sid = "e0fdb2b6-f6b5-4d3a-808a-6d55ff5328c7"; } 
                            attribute :>> interfaceName = "Wheel Housing to Uplock Sensor 2"; 
                             
                        }  
                        interface 'bb425b5f-290b-4518-a534-23695d60b84d' : PhysicalLink 
                            connect sourcePhysicalPort ::> 'NLG Wheel Housing and Assembly'.'PP 7'
                            to targetPhysicalPort ::> 'NLG Uplock Sensor 1'.'PP 1' {
                            @CapellaID { eid = "bb425b5f-290b-4518-a534-23695d60b84d"; sid = "bb425b5f-290b-4518-a534-23695d60b84d"; } 
                            attribute :>> interfaceName = "Wheel Housing to Uplock Sensor 1"; 
                             
                        }  
                        interface '36410711-a37e-446e-963f-95d50661455d' : PhysicalLink 
                            connect sourcePhysicalPort ::> 'NLG Door Selector Valve'.'PP 3'
                            to targetPhysicalPort ::> 'NLG Door Actuator'.'PP 4' {
                            @CapellaID { eid = "36410711-a37e-446e-963f-95d50661455d"; } 
                            attribute :>> interfaceName = "NLG Door Selector Valve to NLG Door Actuator"; 
                             
                             
                        }  
                        part 'NLG Wheel Housing and Assembly' : PhysicalComponent { 
                            @CapellaID { eid = "61ab0f0b-2b23-4c5e-853e-800d89976b25"; sid = "61ab0f0b-2b23-4c5e-853e-800d89976b25"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "50f75b76-7da9-4d5b-9428-fa7799568b7c"; sid = "50f75b76-7da9-4d5b-9428-fa7799568b7c"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '10216126-1aa6-41a9-b27c-ceb62e496dc0' : ComponentPortAllocation
                                    allocate allocatedPort ::> 'PP 1'
                                    to allocatingPort ::> 'Nose Landing Gear Library'::'Nose Landing Gear'::'Physical Architecture'::'Structure'::'Physical System'.'Behavior Parent'.'NLG Wheel'.'CP 1' { 
                                    @CapellaID { eid = "10216126-1aa6-41a9-b27c-ceb62e496dc0"; } 
                                     
                                }  
                                 
                                ref :>> ownedComponentPortAllocations =  ('10216126-1aa6-41a9-b27c-ceb62e496dc0'); 
                            }  
                            port 'PP 2' : PhysicalPort { 
                                @CapellaID { eid = "57dab957-0719-4d48-8268-718e9ca6b671"; sid = "57dab957-0719-4d48-8268-718e9ca6b671"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 3' : PhysicalPort { 
                                @CapellaID { eid = "0c8d7f46-5af3-4e02-9893-ef64144fb6a5"; sid = "0c8d7f46-5af3-4e02-9893-ef64144fb6a5"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation 'b44e0906-356f-4684-be23-bb4abfc7f043' : ComponentPortAllocation
                                    allocate allocatedPort ::> 'PP 3'
                                    to allocatingPort ::> 'Nose Landing Gear Library'::'Nose Landing Gear'::'Physical Architecture'::'Structure'::'Physical System'.'Behavior Parent'.'NLG Wheel'.'CP 2' { 
                                    @CapellaID { eid = "b44e0906-356f-4684-be23-bb4abfc7f043"; } 
                                     
                                }  
                                 
                                ref :>> ownedComponentPortAllocations =  ('b44e0906-356f-4684-be23-bb4abfc7f043'); 
                            }  
                            port 'PP 4' : PhysicalPort { 
                                @CapellaID { eid = "61267105-6aa9-47e4-89cd-080a9070c22b"; sid = "61267105-6aa9-47e4-89cd-080a9070c22b"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '914a03bd-ed9b-47e5-9183-402bcf729613' : ComponentPortAllocation
                                    allocate allocatedPort ::> 'PP 4'
                                    to allocatingPort ::> 'Nose Landing Gear Library'::'Nose Landing Gear'::'Physical Architecture'::'Structure'::'Physical System'.'Behavior Parent'.'NLG Wheel'.'CP 3' { 
                                    @CapellaID { eid = "914a03bd-ed9b-47e5-9183-402bcf729613"; } 
                                     
                                }  
                                 
                                ref :>> ownedComponentPortAllocations =  ('914a03bd-ed9b-47e5-9183-402bcf729613'); 
                            }  
                            port 'PP 5' : PhysicalPort { 
                                @CapellaID { eid = "91fd159e-52f5-4296-8700-2701cd29b258"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '06b33400-ec85-4e28-9790-3a2ded40816c' : ComponentPortAllocation
                                    allocate allocatedPort ::> 'PP 5'
                                    to allocatingPort ::> 'Nose Landing Gear Library'::'Nose Landing Gear'::'Physical Architecture'::'Structure'::'Physical System'.'Behavior Parent'.'NLG Wheel'.'CP 4' { 
                                    @CapellaID { eid = "06b33400-ec85-4e28-9790-3a2ded40816c"; } 
                                     
                                }  
                                 
                                ref :>> ownedComponentPortAllocations =  ('06b33400-ec85-4e28-9790-3a2ded40816c'); 
                            }  
                            port 'PP 8' : PhysicalPort { 
                                @CapellaID { eid = "5505dff9-b352-4625-8ca5-b37decaadd25"; sid = "5505dff9-b352-4625-8ca5-b37decaadd25"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 6' : PhysicalPort { 
                                @CapellaID { eid = "d899934c-b972-409a-9713-e3846a8b8d78"; sid = "d899934c-b972-409a-9713-e3846a8b8d78"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 9' : PhysicalPort { 
                                @CapellaID { eid = "1a1b7ac2-34a8-48e0-b97f-a3512315bc09"; sid = "1a1b7ac2-34a8-48e0-b97f-a3512315bc09"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 7' : PhysicalPort { 
                                @CapellaID { eid = "5b9cdf84-541a-4a95-be7e-b1b2714dc758"; sid = "5b9cdf84-541a-4a95-be7e-b1b2714dc758"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                             
                        }  
                        part 'NLG Door Actuator' : PhysicalComponent { 
                            @CapellaID { eid = "e13c5a2b-7325-4fb5-94aa-ff1c152c0aec"; sid = "e13c5a2b-7325-4fb5-94aa-ff1c152c0aec"; } 
                            attribute :>> isAbstract = false; 
                            attribute :>> isActor = false; 
                            attribute :>> isHuman = false; 
                            attribute :>> kind = PhysicalComponentKind::UNSET; 
                            attribute :>> nature = PhysicalComponentNature::NODE; 
                            port 'PP 2' : PhysicalPort { 
                                @CapellaID { eid = "534dea41-d4b2-4980-8149-508de96e2893"; sid = "534dea41-d4b2-4980-8149-508de96e2893"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 3' : PhysicalPort { 
                                @CapellaID { eid = "b3482641-6992-48bc-b933-59eb23cda035"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation 'cadd1adc-b7f8-4e8d-b13d-50b9ba45bd2e' : ComponentPortAllocation
                                    allocate allocatedPort ::> 'PP 3'
                                    to allocatingPort ::> 'Nose Landing Gear Library'::'Nose Landing Gear'::'Physical Architecture'::'Structure'::'Physical System'.'Behavior Parent'.'NLG Door Actuator'.'CP 1' { 
                                    @CapellaID { eid = "cadd1adc-b7f8-4e8d-b13d-50b9ba45bd2e"; } 
                                     
                                }  
                                 
                                ref :>> ownedComponentPortAllocations =  ('cadd1adc-b7f8-4e8d-b13d-50b9ba45bd2e'); 
                            }  
                            port 'PP 4' : PhysicalPort { 
                                @CapellaID { eid = "f662b882-b56a-4aba-9741-fb4e8073deaa"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation 'ea967683-bb1c-489d-b1dd-f76623e4cf29' : ComponentPortAllocation
                                    allocate allocatedPort ::> 'PP 4'
                                    to allocatingPort ::> 'Nose Landing Gear Library'::'Nose Landing Gear'::'Physical Architecture'::'Structure'::'Physical System'.'Behavior Parent'.'NLG Door Actuator'.'CP 2' { 
                                    @CapellaID { eid = "ea967683-bb1c-489d-b1dd-f76623e4cf29"; } 
                                     
                                }  
                                 
                                ref :>> ownedComponentPortAllocations =  ('ea967683-bb1c-489d-b1dd-f76623e4cf29'); 
                            }  
                             
                        }  
                        part 'NLG Downlock Sensor 2' : PhysicalComponent { 
                            @CapellaID { eid = "09723b21-ede3-4eb7-8767-37ef6b7716eb"; sid = "09723b21-ede3-4eb7-8767-37ef6b7716eb"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "037b6820-ec03-4412-8171-244f696ddfcf"; sid = "037b6820-ec03-4412-8171-244f696ddfcf"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 2' : PhysicalPort { 
                                @CapellaID { eid = "5a007706-4a0b-480d-9d44-d5cf788eea0d"; sid = "5a007706-4a0b-480d-9d44-d5cf788eea0d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                             
                        }  
                        part 'NLG  Actuator' : PhysicalComponent { 
                            doc /*
                            <p>Hydraulic Cylider</p>

                            */ 
                            @CapellaID { eid = "de2e61b4-19ce-4353-84e5-3df7849f0213"; sid = "de2e61b4-19ce-4353-84e5-3df7849f0213"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "15a2f7e9-9a70-47e6-b227-7d39445b9273"; sid = "15a2f7e9-9a70-47e6-b227-7d39445b9273"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation 'bd0409f3-af3c-4a46-98d0-214fe890ce7d' : ComponentPortAllocation
                                    allocate allocatedPort ::> 'PP 1'
                                    to allocatingPort ::> 'Nose Landing Gear Library'::'Nose Landing Gear'::'Physical Architecture'::'Structure'::'Physical System'.'Behavior Parent'.'NLG Wheel Steerin'.'CP 1' { 
                                    @CapellaID { eid = "bd0409f3-af3c-4a46-98d0-214fe890ce7d"; } 
                                     
                                }  
                                 
                                ref :>> ownedComponentPortAllocations =  ('bd0409f3-af3c-4a46-98d0-214fe890ce7d'); 
                            }  
                            port 'PP 2' : PhysicalPort { 
                                @CapellaID { eid = "e67ddfc8-8b32-44a9-a3c4-e4e24a59a03e"; sid = "e67ddfc8-8b32-44a9-a3c4-e4e24a59a03e"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '4b169ef6-b0da-41f7-87bc-6872b7ccc362' : ComponentPortAllocation
                                    allocate allocatedPort ::> 'PP 2'
                                    to allocatingPort ::> 'Nose Landing Gear Library'::'Nose Landing Gear'::'Physical Architecture'::'Structure'::'Physical System'.'Behavior Parent'.'NLG Wheel Steerin'.'CP 2' { 
                                    @CapellaID { eid = "4b169ef6-b0da-41f7-87bc-6872b7ccc362"; } 
                                     
                                }  
                                 
                                ref :>> ownedComponentPortAllocations =  ('4b169ef6-b0da-41f7-87bc-6872b7ccc362'); 
                            }  
                             
                        }  
                        part 'NLG Uplock Sensor 2' : PhysicalComponent { 
                            @CapellaID { eid = "42550fa6-d7a1-4c42-9e63-11a02377980b"; sid = "42550fa6-d7a1-4c42-9e63-11a02377980b"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "2898bd76-0e0b-4321-a03f-7bb91813ddd4"; sid = "2898bd76-0e0b-4321-a03f-7bb91813ddd4"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 2' : PhysicalPort { 
                                @CapellaID { eid = "c8db00bb-6f5d-41af-b128-6b27c1478e58"; sid = "c8db00bb-6f5d-41af-b128-6b27c1478e58"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                             
                        }  
                        part 'NLG Doors Dump Valve' : PhysicalComponent { 
                            @CapellaID { eid = "a1cc9b48-0481-439c-91b0-8f34d116c46d"; sid = "a1cc9b48-0481-439c-91b0-8f34d116c46d"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "9304e89e-9e88-446f-b821-971cf3a888a3"; sid = "9304e89e-9e88-446f-b821-971cf3a888a3"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '4e12292b-6fd0-4bc2-b4c0-d4d26d9918e3' : ComponentPortAllocation
                                    allocate allocatedPort ::> 'PP 1'
                                    to allocatingPort ::> 'Nose Landing Gear Library'::'Nose Landing Gear'::'Physical Architecture'::'Structure'::'Physical System'.'Behavior Parent'.'NLG Doors Dump Valve'.'CP 2' { 
                                    @CapellaID { eid = "4e12292b-6fd0-4bc2-b4c0-d4d26d9918e3"; } 
                                     
                                }  
                                 
                                ref :>> ownedComponentPortAllocations =  ('4e12292b-6fd0-4bc2-b4c0-d4d26d9918e3'); 
                            }  
                            port 'PP 2' : PhysicalPort { 
                                @CapellaID { eid = "f6152ec3-f70b-4693-af4d-554e14982d9c"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '2231a8b6-60be-4bcd-be78-e694601514bc' : ComponentPortAllocation
                                    allocate allocatedPort ::> 'PP 2'
                                    to allocatingPort ::> 'Nose Landing Gear Library'::'Nose Landing Gear'::'Physical Architecture'::'Structure'::'Physical System'.'Behavior Parent'.'NLG Doors Dump Valve'.'CP 1' { 
                                    @CapellaID { eid = "2231a8b6-60be-4bcd-be78-e694601514bc"; } 
                                     
                                }  
                                 
                                ref :>> ownedComponentPortAllocations =  ('2231a8b6-60be-4bcd-be78-e694601514bc'); 
                            }  
                            port 'PP 3' : PhysicalPort { 
                                @CapellaID { eid = "c251b70a-a3d7-48fc-9e12-56358ce95a73"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation 'e9c55a8b-51a2-48be-8abc-3b05708bd876' : ComponentPortAllocation
                                    allocate allocatedPort ::> 'PP 3'
                                    to allocatingPort ::> 'Nose Landing Gear Library'::'Nose Landing Gear'::'Physical Architecture'::'Structure'::'Physical System'.'Behavior Parent'.'NLG Doors Dump Valve'.'CP 3' { 
                                    @CapellaID { eid = "e9c55a8b-51a2-48be-8abc-3b05708bd876"; } 
                                     
                                }  
                                 
                                ref :>> ownedComponentPortAllocations =  ('e9c55a8b-51a2-48be-8abc-3b05708bd876'); 
                            }  
                             
                        }  
                        part 'NLG Uplock Sensor 1' : PhysicalComponent { 
                            @CapellaID { eid = "96cb3652-544d-4ac3-a718-5c48a386628f"; sid = "96cb3652-544d-4ac3-a718-5c48a386628f"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "6e8e2f2a-a887-4aa8-91b6-5f110c6c8a5e"; sid = "6e8e2f2a-a887-4aa8-91b6-5f110c6c8a5e"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 2' : PhysicalPort { 
                                @CapellaID { eid = "3064dd95-d3eb-494c-8a49-2c94ae7f857d"; sid = "3064dd95-d3eb-494c-8a49-2c94ae7f857d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part 'fc4095fd-0b17-4ade-ab54-146695109d2a' : CPart :> 'NLG Downlock Sensor 1'  { 
                                @CapellaID { eid = "fc4095fd-0b17-4ade-ab54-146695109d2a"; sid = "fc4095fd-0b17-4ade-ab54-146695109d2a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                allocation '5686a0eb-df6c-453f-9fcd-1b7f2385c288' : PartDeploymentLink
                                    allocate deployedElement ::> 'Behavior Parent'.'50c7b57a-d789-4f03-9a43-10cf58c245bd'
                                    to location ::> 'Nose Landing Gear Library'::'Nose Landing Gear'::'Physical Architecture'::'Structure'::'Physical System'.'Nose Landing Gear'.'NLG Uplock Sensor 1'.'fc4095fd-0b17-4ade-ab54-146695109d2a' { 
                                    @CapellaID { eid = "5686a0eb-df6c-453f-9fcd-1b7f2385c288"; } 
                                     
                                }  
                                ref :>> ownedDeploymentLinks =  ('5686a0eb-df6c-453f-9fcd-1b7f2385c288'); 
                                 
                            }  
                            part 'NLG Downlock Sensor 1' : PhysicalComponent { 
                                @CapellaID { eid = "f540a33e-d166-4593-9860-77309e6e02ef"; sid = "f540a33e-d166-4593-9860-77309e6e02ef"; } 
                                attribute :>> isAbstract = false; 
                                attribute :>> isActor = false; 
                                attribute :>> isHuman = false; 
                                attribute :>> kind = PhysicalComponentKind::UNSET; 
                                attribute :>> nature = PhysicalComponentNature::NODE; 
                                port 'PP 1' : PhysicalPort { 
                                    @CapellaID { eid = "bf7c869f-f3fc-4890-b19f-758cf976622f"; sid = "bf7c869f-f3fc-4890-b19f-758cf976622f"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                     
                                }  
                                port 'PP 2' : PhysicalPort { 
                                    @CapellaID { eid = "165e44aa-098b-4d82-b9c1-936bb3f0156e"; sid = "165e44aa-098b-4d82-b9c1-936bb3f0156e"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                     
                                }  
                                 
                            }  
                             
                            ref :>> ownedPhysicalComponents =  ('NLG Downlock Sensor 1'); 
                        }  
                        part 'NLG Door Sensor' : PhysicalComponent { 
                            @CapellaID { eid = "f989b8ce-627c-42b1-a43b-10eb4b7688a3"; sid = "f989b8ce-627c-42b1-a43b-10eb4b7688a3"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "44f4b3a5-f188-4646-b5c7-b3ec87c3039a"; sid = "44f4b3a5-f188-4646-b5c7-b3ec87c3039a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 2' : PhysicalPort { 
                                @CapellaID { eid = "5524dae1-5f2a-46bc-8535-518c09be23e3"; sid = "5524dae1-5f2a-46bc-8535-518c09be23e3"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                             
                        }  
                        part 'NLG Structural Post Assembly' : PhysicalComponent { 
                            @CapellaID { eid = "ec63ffc8-05b0-465a-9a7c-b52e11db8fa4"; sid = "ec63ffc8-05b0-465a-9a7c-b52e11db8fa4"; } 
                            attribute :>> isAbstract = false; 
                            attribute :>> isActor = false; 
                            attribute :>> isHuman = false; 
                            attribute :>> kind = PhysicalComponentKind::UNSET; 
                            attribute :>> nature = PhysicalComponentNature::NODE; 
                            port 'PP 3' : PhysicalPort { 
                                @CapellaID { eid = "4c591b81-6bd6-4543-8252-c836cd74342d"; sid = "4c591b81-6bd6-4543-8252-c836cd74342d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation 'a6dbb748-6209-414d-a865-b6c6df57dc2b' : ComponentPortAllocation
                                    allocate allocatedPort ::> 'PP 3'
                                    to allocatingPort ::> 'Nose Landing Gear Library'::'Nose Landing Gear'::'Physical Architecture'::'Structure'::'Physical System'.'Behavior Parent'.'NLG Struct Post'.'CP 1' { 
                                    @CapellaID { eid = "a6dbb748-6209-414d-a865-b6c6df57dc2b"; } 
                                     
                                }  
                                 
                                ref :>> ownedComponentPortAllocations =  ('a6dbb748-6209-414d-a865-b6c6df57dc2b'); 
                            }  
                            port 'PP 4' : PhysicalPort { 
                                @CapellaID { eid = "f91f1dc9-6709-4b71-aa93-7bb799409c97"; sid = "f91f1dc9-6709-4b71-aa93-7bb799409c97"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '7cfde47d-66d3-419e-8204-66e2492eba21' : ComponentPortAllocation
                                    allocate allocatedPort ::> 'PP 4'
                                    to allocatingPort ::> 'Nose Landing Gear Library'::'Nose Landing Gear'::'Physical Architecture'::'Structure'::'Physical System'.'Behavior Parent'.'NLG Struct Post'.'CP 3' { 
                                    @CapellaID { eid = "7cfde47d-66d3-419e-8204-66e2492eba21"; } 
                                     
                                }  
                                 
                                ref :>> ownedComponentPortAllocations =  ('7cfde47d-66d3-419e-8204-66e2492eba21'); 
                            }  
                            port 'PP 5' : PhysicalPort { 
                                @CapellaID { eid = "421970f8-0c30-4f06-b3e1-df7073223e0e"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '8892e48f-5e8a-4dbb-8b6c-b38ba1a8336f' : ComponentPortAllocation
                                    allocate allocatedPort ::> 'PP 5'
                                    to allocatingPort ::> 'Nose Landing Gear Library'::'Nose Landing Gear'::'Physical Architecture'::'Structure'::'Physical System'.'Behavior Parent'.'NLG Struct Post'.'CP 2' { 
                                    @CapellaID { eid = "8892e48f-5e8a-4dbb-8b6c-b38ba1a8336f"; } 
                                     
                                }  
                                 
                                ref :>> ownedComponentPortAllocations =  ('8892e48f-5e8a-4dbb-8b6c-b38ba1a8336f'); 
                            }  
                             
                        }  
                        part 'NLG Door Selector Valve' : PhysicalComponent { 
                            doc /*
                            Node component housing the NLG Doors Selector Valve behavior. Receives regulated hydraulic supply and routes it, per commanded door state, to the NLG door actuator and the dump valve.
                            */ 
                            @CapellaID { eid = "9bbe1b0a-b72b-4bd0-9822-416d2d598c15"; sid = "9bbe1b0a-b72b-4bd0-9822-416d2d598c15"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "45d04b9b-f3c0-4d1e-82e3-a9d2da6ad154"; sid = "45d04b9b-f3c0-4d1e-82e3-a9d2da6ad154"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '6044b194-8672-4b75-91ac-f6e2eae83de6' : ComponentPortAllocation
                                    allocate allocatedPort ::> 'PP 1'
                                    to allocatingPort ::> 'Nose Landing Gear Library'::'Nose Landing Gear'::'Physical Architecture'::'Structure'::'Physical System'.'Behavior Parent'.'NLG Doors Selector Valve'.'CP 4' { 
                                    @CapellaID { eid = "6044b194-8672-4b75-91ac-f6e2eae83de6"; } 
                                     
                                }  
                                 
                                ref :>> ownedComponentPortAllocations =  ('6044b194-8672-4b75-91ac-f6e2eae83de6'); 
                            }  
                            port 'PP 2' : PhysicalPort { 
                                @CapellaID { eid = "a75c62d8-f09d-431c-bab2-c2ec06bef833"; sid = "a75c62d8-f09d-431c-bab2-c2ec06bef833"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation 'abd67014-d0ae-48fb-b9a3-49d4616c829f' : ComponentPortAllocation
                                    allocate allocatedPort ::> 'PP 2'
                                    to allocatingPort ::> 'Nose Landing Gear Library'::'Nose Landing Gear'::'Physical Architecture'::'Structure'::'Physical System'.'Behavior Parent'.'NLG Doors Selector Valve'.'CP 3' { 
                                    @CapellaID { eid = "abd67014-d0ae-48fb-b9a3-49d4616c829f"; } 
                                     
                                }  
                                 
                                ref :>> ownedComponentPortAllocations =  ('abd67014-d0ae-48fb-b9a3-49d4616c829f'); 
                            }  
                            port 'PP 3' : PhysicalPort { 
                                @CapellaID { eid = "27cc89d0-4384-4d87-ba0a-b0000a01965a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '3165cc45-4b61-486c-b9e2-15df43a631d1' : ComponentPortAllocation
                                    allocate allocatedPort ::> 'PP 3'
                                    to allocatingPort ::> 'Nose Landing Gear Library'::'Nose Landing Gear'::'Physical Architecture'::'Structure'::'Physical System'.'Behavior Parent'.'NLG Doors Selector Valve'.'CP 2' { 
                                    @CapellaID { eid = "3165cc45-4b61-486c-b9e2-15df43a631d1"; } 
                                     
                                }  
                                 
                                ref :>> ownedComponentPortAllocations =  ('3165cc45-4b61-486c-b9e2-15df43a631d1'); 
                            }  
                             
                        }  
                        part 'NLG Shock Absorber' : PhysicalComponent { 
                            @CapellaID { eid = "8560703b-e78b-478b-8bab-5d67cf701527"; sid = "8560703b-e78b-478b-8bab-5d67cf701527"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "dc57d1db-b5e1-4fe9-9f07-ff5c4819ef66"; sid = "dc57d1db-b5e1-4fe9-9f07-ff5c4819ef66"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '2a0bac44-5b9c-475d-8f33-1ae328b4e221' : ComponentPortAllocation
                                    allocate allocatedPort ::> 'PP 1'
                                    to allocatingPort ::> 'Nose Landing Gear Library'::'Nose Landing Gear'::'Physical Architecture'::'Structure'::'Physical System'.'Behavior Parent'.'NLG Shock'.'CP 1' { 
                                    @CapellaID { eid = "2a0bac44-5b9c-475d-8f33-1ae328b4e221"; } 
                                     
                                }  
                                 
                                ref :>> ownedComponentPortAllocations =  ('2a0bac44-5b9c-475d-8f33-1ae328b4e221'); 
                            }  
                            port 'PP 2' : PhysicalPort { 
                                @CapellaID { eid = "7342eb4a-21b3-46b0-adb0-2998b454eade"; sid = "7342eb4a-21b3-46b0-adb0-2998b454eade"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 3' : PhysicalPort { 
                                @CapellaID { eid = "7d1ccf5b-9670-4eff-9071-39996bac485d"; sid = "7d1ccf5b-9670-4eff-9071-39996bac485d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 4' : PhysicalPort { 
                                @CapellaID { eid = "891b152b-23eb-4e07-a97b-622bfd41f21c"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation 'f07da7e2-218c-4fd8-9a27-b12eeb312bd0' : ComponentPortAllocation
                                    allocate allocatedPort ::> 'PP 4'
                                    to allocatingPort ::> 'Nose Landing Gear Library'::'Nose Landing Gear'::'Physical Architecture'::'Structure'::'Physical System'.'Behavior Parent'.'NLG Shock'.'CP 2' { 
                                    @CapellaID { eid = "f07da7e2-218c-4fd8-9a27-b12eeb312bd0"; } 
                                     
                                }  
                                 
                                ref :>> ownedComponentPortAllocations =  ('f07da7e2-218c-4fd8-9a27-b12eeb312bd0'); 
                            }  
                             
                        }  
                        part 'Weight on Wheel Sensor 1' : PhysicalComponent { 
                            @CapellaID { eid = "d9ec9bc4-17ef-4866-828b-7ceb4ca034c8"; sid = "d9ec9bc4-17ef-4866-828b-7ceb4ca034c8"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "86976df7-c65b-4caa-912d-d05c8a758e5b"; sid = "86976df7-c65b-4caa-912d-d05c8a758e5b"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 2' : PhysicalPort { 
                                @CapellaID { eid = "635e5366-f798-4a32-9972-386a8f874eab"; sid = "635e5366-f798-4a32-9972-386a8f874eab"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation 'b485eee3-f141-42d0-988a-c17d0a0113e5' : ComponentPortAllocation
                                    allocate allocatedPort ::> 'PP 2'
                                    to allocatingPort ::> 'Nose Landing Gear Library'::'Nose Landing Gear'::'Physical Architecture'::'Structure'::'Physical System'.'Behavior Parent'.'Weight on Wheel Sensor 1'.'CP 1' { 
                                    @CapellaID { eid = "b485eee3-f141-42d0-988a-c17d0a0113e5"; } 
                                     
                                }  
                                 
                                ref :>> ownedComponentPortAllocations =  ('b485eee3-f141-42d0-988a-c17d0a0113e5'); 
                            }  
                             
                        }  
                        part 'Weight on Wheel Sensor 2' : PhysicalComponent { 
                            @CapellaID { eid = "c4524907-1c4b-40e9-b2be-f49ef79bbbf4"; sid = "c4524907-1c4b-40e9-b2be-f49ef79bbbf4"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "ef81b0f4-813a-4f43-9e53-7fd56454a041"; sid = "ef81b0f4-813a-4f43-9e53-7fd56454a041"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 2' : PhysicalPort { 
                                @CapellaID { eid = "2c4d6001-1f1b-4de4-909e-3f77033a9cce"; sid = "2c4d6001-1f1b-4de4-909e-3f77033a9cce"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                             
                        }  
                        part 'Landing Gear Control and Indication Computer' : PhysicalComponent { 
                            @CapellaID { eid = "7c90cca3-72bc-4c73-b935-2aa1c491c5b1"; sid = "7c90cca3-72bc-4c73-b935-2aa1c491c5b1"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "4651498b-e970-4eba-91de-5366c804e371"; sid = "4651498b-e970-4eba-91de-5366c804e371"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 2' : PhysicalPort { 
                                @CapellaID { eid = "f525113f-6f7a-43aa-881c-14109bfa0926"; sid = "f525113f-6f7a-43aa-881c-14109bfa0926"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 3' : PhysicalPort { 
                                @CapellaID { eid = "b1209235-f731-4330-8e05-ec24d7254761"; sid = "b1209235-f731-4330-8e05-ec24d7254761"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 4' : PhysicalPort { 
                                @CapellaID { eid = "a7497dd1-b716-45a4-a3b8-586185397c40"; sid = "a7497dd1-b716-45a4-a3b8-586185397c40"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 5' : PhysicalPort { 
                                @CapellaID { eid = "f724e455-f7c6-4850-a613-996174961e06"; sid = "f724e455-f7c6-4850-a613-996174961e06"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 6' : PhysicalPort { 
                                @CapellaID { eid = "c9d16183-42eb-4d12-bb69-abe64ef6c059"; sid = "c9d16183-42eb-4d12-bb69-abe64ef6c059"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '0664a757-87cf-4022-9ec4-825ed86dba1b' : ComponentPortAllocation
                                    allocate allocatedPort ::> 'PP 6'
                                    to allocatingPort ::> 'Nose Landing Gear Library'::'Nose Landing Gear'::'Physical Architecture'::'Structure'::'Physical System'.'Nose Landing Gear'.'Landing Gear Control and Indication Computer'.'Landing Gear Control and Indication Computer 1'.'CP 2' { 
                                    @CapellaID { eid = "0664a757-87cf-4022-9ec4-825ed86dba1b"; } 
                                     
                                }  
                                 
                                ref :>> ownedComponentPortAllocations =  ('0664a757-87cf-4022-9ec4-825ed86dba1b'); 
                            }  
                            port 'PP 7' : PhysicalPort { 
                                @CapellaID { eid = "02522189-4657-460d-8658-b234da735391"; sid = "02522189-4657-460d-8658-b234da735391"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 8' : PhysicalPort { 
                                @CapellaID { eid = "6f211474-5602-484c-9fa2-26feab58fd60"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'PP 9' : PhysicalPort { 
                                @CapellaID { eid = "0b36e081-6db5-4453-9ddd-d582d21a5d5d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part 'eb7da3b1-ba85-4a01-b68f-2f17b0c9549e' : CPart :> 'Landing Gear Control and Indication Computer 1'  { 
                                @CapellaID { eid = "eb7da3b1-ba85-4a01-b68f-2f17b0c9549e"; sid = "eb7da3b1-ba85-4a01-b68f-2f17b0c9549e"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part 'Landing Gear Control and Indication Computer 1' : PhysicalComponent { 
                                @CapellaID { eid = "270292bc-dc80-40fa-9dd7-43cf3256b95c"; sid = "270292bc-dc80-40fa-9dd7-43cf3256b95c"; } 
                                attribute :>> isAbstract = false; 
                                attribute :>> isActor = false; 
                                attribute :>> isHuman = false; 
                                attribute :>> kind = PhysicalComponentKind::UNSET; 
                                attribute :>> nature = PhysicalComponentNature::BEHAVIOR; 
                                allocation 'ab1c82a0-a1cd-41da-a9e2-3685403ba7ed' : ComponentFunctionalAllocation
                                    allocate function ::> 'Physical Functions'::'Root Physical Function'.'Provide Landing Gear Indication'.'Provide'
                                    to component ::> 'Landing Gear Control and Indication Computer 1' { 
                                    @CapellaID { eid = "ab1c82a0-a1cd-41da-a9e2-3685403ba7ed"; sid = "ab1c82a0-a1cd-41da-a9e2-3685403ba7ed"; } 
                                     
                                } 
                                perform 'Physical Functions'::'Root Physical Function'.'Provide Landing Gear Indication'.'Provide' ; 
                                allocation 'dbde030a-0d08-4a3f-ba67-3f7c93f2358a' : ComponentFunctionalAllocation
                                    allocate function ::> 'Physical Functions'::'Root Physical Function'.'Sense NLG State'
                                    to component ::> 'Landing Gear Control and Indication Computer 1' { 
                                    @CapellaID { eid = "dbde030a-0d08-4a3f-ba67-3f7c93f2358a"; sid = "dbde030a-0d08-4a3f-ba67-3f7c93f2358a"; } 
                                     
                                } 
                                perform 'Physical Functions'::'Root Physical Function'.'Sense NLG State' ; 
                                allocation 'fe5f4565-d03b-482c-bffb-6a62f889d815' : ComponentFunctionalAllocation
                                    allocate function ::> 'Physical Functions'::'Root Physical Function'.'Manage NLG'
                                    to component ::> 'Landing Gear Control and Indication Computer 1' { 
                                    @CapellaID { eid = "fe5f4565-d03b-482c-bffb-6a62f889d815"; } 
                                     
                                } 
                                perform 'Physical Functions'::'Root Physical Function'.'Manage NLG' ; 
                                allocation 'dde15bfe-2f60-4905-92a9-1d14cc910610' : ComponentFunctionalAllocation
                                    allocate function ::> 'Physical Functions'::'Root Physical Function'.'Manage NLG Door'
                                    to component ::> 'Landing Gear Control and Indication Computer 1' { 
                                    @CapellaID { eid = "dde15bfe-2f60-4905-92a9-1d14cc910610"; } 
                                     
                                } 
                                perform 'Physical Functions'::'Root Physical Function'.'Manage NLG Door' ; 
                                port 'CP 1' : ComponentPort { 
                                    @CapellaID { eid = "ba5623bc-1b19-4da4-a49a-822ae2abb4e4"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                     
                                }  
                                port 'CP 2' : ComponentPort { 
                                    @CapellaID { eid = "e4faf188-05b1-4f59-b498-6e4b6b5ecc1b"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation 'c8399a71-0b2e-4680-b805-16ffe754a3b7' : PortAllocation
                                        allocate allocatedPort ::> 'Physical Functions'::'Root Physical Function'.'Sense NLG State'.'FIP 21'
                                        to allocatingPort ::> 'CP 2'; 
                                    ref :>> ownedPortAllocations =  ('c8399a71-0b2e-4680-b805-16ffe754a3b7'); 
                                     
                                }  
                                port 'CP 3' : ComponentPort { 
                                    @CapellaID { eid = "83455c2b-b207-4d73-9141-f26d209459b7"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation 'eaeed06d-eb91-44c2-86e7-d487960d9d36' : PortAllocation
                                        allocate allocatedPort ::> 'Physical Functions'::'Root Physical Function'.'Sense NLG State'.'FIP 22'
                                        to allocatingPort ::> 'CP 3'; 
                                    ref :>> ownedPortAllocations =  ('eaeed06d-eb91-44c2-86e7-d487960d9d36'); 
                                     
                                }  
                                port 'CP 4' : ComponentPort { 
                                    @CapellaID { eid = "e2c48a0d-0880-4935-a2eb-5f582b25009a"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '20760074-6695-4dd5-b232-1018910185b5' : PortAllocation
                                        allocate allocatedPort ::> 'Physical Functions'::'Root Physical Function'.'Sense NLG State'.'FIP 2'
                                        to allocatingPort ::> 'CP 4'; 
                                    ref :>> ownedPortAllocations =  ('20760074-6695-4dd5-b232-1018910185b5'); 
                                     
                                }  
                                port 'CP 5' : ComponentPort { 
                                    @CapellaID { eid = "224e675d-b169-493f-b331-376898463953"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation 'a2b38866-62c3-45b4-8be9-678571dc1b6a' : PortAllocation
                                        allocate allocatedPort ::> 'Physical Functions'::'Root Physical Function'.'Sense NLG State'.'FIP 5'
                                        to allocatingPort ::> 'CP 5'; 
                                    ref :>> ownedPortAllocations =  ('a2b38866-62c3-45b4-8be9-678571dc1b6a'); 
                                     
                                }  
                                port 'CP 6' : ComponentPort { 
                                    @CapellaID { eid = "1c549838-5a9d-40a8-a576-8d59ed9516f6"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '5b857c79-12e2-4258-b271-e315fa3b173f' : PortAllocation
                                        allocate allocatedPort ::> 'Physical Functions'::'Root Physical Function'.'Sense NLG State'.'FIP 3'
                                        to allocatingPort ::> 'CP 6'; 
                                    ref :>> ownedPortAllocations =  ('5b857c79-12e2-4258-b271-e315fa3b173f'); 
                                     
                                }  
                                port 'CP 7' : ComponentPort { 
                                    @CapellaID { eid = "c506acb5-ec01-44b3-9cb2-cc5f42595f13"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation 'a2dc8027-9154-4fdd-877b-82a39c50bbb3' : PortAllocation
                                        allocate allocatedPort ::> 'Physical Functions'::'Root Physical Function'.'Sense NLG State'.'FIP 4'
                                        to allocatingPort ::> 'CP 7'; 
                                    ref :>> ownedPortAllocations =  ('a2dc8027-9154-4fdd-877b-82a39c50bbb3'); 
                                     
                                }  
                                port 'CP 8' : ComponentPort { 
                                    @CapellaID { eid = "d180838d-81ad-4e2a-a8ed-0e828cec55ea"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::OUT; 
                                    attribute :>> isUnique = false; 
                                    ref allocation 'e785ab7d-b876-4611-99e8-5d8dbcb1dc0a' : PortAllocation
                                        allocate allocatedPort ::> 'Physical Functions'::'Root Physical Function'.'Manage NLG'.'FOP 1'
                                        to allocatingPort ::> 'CP 8'; 
                                    ref :>> ownedPortAllocations =  ('e785ab7d-b876-4611-99e8-5d8dbcb1dc0a'); 
                                     
                                }  
                                port 'CP 9' : ComponentPort { 
                                    @CapellaID { eid = "5c8a9612-b915-4088-b61a-3117d698931c"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '9a4c37ea-cbbe-4c7e-80b8-8bd39de3b2ed' : PortAllocation
                                        allocate allocatedPort ::> 'Physical Functions'::'Root Physical Function'.'Sense NLG State'.'FIP 20'
                                        to allocatingPort ::> 'CP 9'; 
                                    ref :>> ownedPortAllocations =  ('9a4c37ea-cbbe-4c7e-80b8-8bd39de3b2ed'); 
                                     
                                }  
                                ref :>> ownedFunctionalAllocation =  ('ab1c82a0-a1cd-41da-a9e2-3685403ba7ed',
                                'dbde030a-0d08-4a3f-ba67-3f7c93f2358a',
                                'fe5f4565-d03b-482c-bffb-6a62f889d815',
                                'dde15bfe-2f60-4905-92a9-1d14cc910610'); 
                                 
                                 
                            }  
                             
                            ref :>> ownedPhysicalComponents =  ('Landing Gear Control and Indication Computer 1'); 
                        }  
                        ref :>> ownedPhysicalLinks =  ('2bf670a3-1ba2-4182-9dad-471d5689b95e',
                        '8c140267-99e2-4152-ae9c-967ed595e955',
                        '7a1be218-3fb5-47d1-adea-529032a8b5ec',
                        'e0fdb2b6-f6b5-4d3a-808a-6d55ff5328c7',
                        'bb425b5f-290b-4518-a534-23695d60b84d',
                        '36410711-a37e-446e-963f-95d50661455d'); 
                         
                        ref :>> ownedPhysicalComponents =  ('NLG Wheel Housing and Assembly',
                        'NLG Door Actuator',
                        'NLG Downlock Sensor 2',
                        'NLG  Actuator',
                        'NLG Uplock Sensor 2',
                        'NLG Doors Dump Valve',
                        'NLG Uplock Sensor 1',
                        'NLG Door Sensor',
                        'NLG Structural Post Assembly',
                        'NLG Door Selector Valve',
                        'NLG Shock Absorber',
                        'Weight on Wheel Sensor 1',
                        'Weight on Wheel Sensor 2',
                        'Landing Gear Control and Indication Computer'); 
                    }  
                    part 'Port Com Bus' : PhysicalComponent { 
                        @CapellaID { eid = "4fbf302c-00f2-43b2-a1a1-2e61703d4d3e"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "310bc900-4f70-4b1f-92e3-26e53c3b0745"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 2' : PhysicalPort { 
                            @CapellaID { eid = "9b8201a4-ef7a-4197-a060-c885986b9dae"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                         
                    }  
                    part 'NLG Door' : PhysicalComponent { 
                        @CapellaID { eid = "46d0204f-f304-4a01-98e2-3e6af3c973c9"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "4f8b93ba-e449-42e6-8baf-5efb78f287d8"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '7add04ba-7fb9-4104-b25e-810023e74d6a' : ComponentPortAllocation
                                allocate allocatedPort ::> 'PP 1'
                                to allocatingPort ::> 'Nose Landing Gear Library'::'Nose Landing Gear'::'Physical Architecture'::'Structure'::'Physical System'.'Behavior Parent'.'Fuel and Power System'.'NLG Door'.'CP 1' { 
                                @CapellaID { eid = "7add04ba-7fb9-4104-b25e-810023e74d6a"; } 
                                 
                            }  
                             
                            ref :>> ownedComponentPortAllocations =  ('7add04ba-7fb9-4104-b25e-810023e74d6a'); 
                        }  
                        port 'PP 2' : PhysicalPort { 
                            @CapellaID { eid = "a47c446d-76a1-4d5d-a526-990f80b24f03"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '55ad5bb2-008e-40fe-b433-1c7143c195e0' : ComponentPortAllocation
                                allocate allocatedPort ::> 'PP 2'
                                to allocatingPort ::> 'Nose Landing Gear Library'::'Nose Landing Gear'::'Physical Architecture'::'Structure'::'Physical System'.'Behavior Parent'.'Fuel and Power System'.'NLG Door'.'CP 2' { 
                                @CapellaID { eid = "55ad5bb2-008e-40fe-b433-1c7143c195e0"; } 
                                 
                            }  
                             
                            ref :>> ownedComponentPortAllocations =  ('55ad5bb2-008e-40fe-b433-1c7143c195e0'); 
                        }  
                         
                    }  
                    part 'H3' : PhysicalComponent { 
                        @CapellaID { eid = "86f330d3-6149-446c-bbc3-aaf7e05854e0"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "c788a90a-8edc-476b-ac20-5f76e803eb22"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '949106c6-49dc-4f8a-ab6a-e40177b49e89' : ComponentPortAllocation
                                allocate allocatedPort ::> 'PP 1'
                                to allocatingPort ::> 'Nose Landing Gear Library'::'Nose Landing Gear'::'Physical Architecture'::'Structure'::'Physical System'.'Behavior Parent'.'H3'.'CP 2' { 
                                @CapellaID { eid = "949106c6-49dc-4f8a-ab6a-e40177b49e89"; } 
                                 
                            }  
                             
                            ref :>> ownedComponentPortAllocations =  ('949106c6-49dc-4f8a-ab6a-e40177b49e89'); 
                        }  
                        port 'PP 2' : PhysicalPort { 
                            @CapellaID { eid = "9464613f-7dea-4c46-9415-ef057badb5a2"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation 'e9845be4-81d4-40bf-897a-7154317af2c4' : ComponentPortAllocation
                                allocate allocatedPort ::> 'PP 2'
                                to allocatingPort ::> 'Nose Landing Gear Library'::'Nose Landing Gear'::'Physical Architecture'::'Structure'::'Physical System'.'Behavior Parent'.'H3'.'CP 1' { 
                                @CapellaID { eid = "e9845be4-81d4-40bf-897a-7154317af2c4"; } 
                                 
                            }  
                             
                            ref :>> ownedComponentPortAllocations =  ('e9845be4-81d4-40bf-897a-7154317af2c4'); 
                        }  
                        port 'PP 3' : PhysicalPort { 
                            @CapellaID { eid = "159fa564-ac54-4f14-9540-7d4d70fd39bd"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '0cbb0151-76b5-473a-92f6-e650da9fbec1' : ComponentPortAllocation
                                allocate allocatedPort ::> 'PP 3'
                                to allocatingPort ::> 'Nose Landing Gear Library'::'Nose Landing Gear'::'Physical Architecture'::'Structure'::'Physical System'.'Behavior Parent'.'H3'.'CP 3' { 
                                @CapellaID { eid = "0cbb0151-76b5-473a-92f6-e650da9fbec1"; } 
                                 
                            }  
                             
                            ref :>> ownedComponentPortAllocations =  ('0cbb0151-76b5-473a-92f6-e650da9fbec1'); 
                        }  
                         
                    }  
                    part 'H2' : PhysicalComponent { 
                        @CapellaID { eid = "46de19fd-24ba-4b82-8d4d-dabda4b7ba96"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "9a51e918-62af-44e7-ac79-12b8fc4afe89"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation 'b4c982bd-20c8-4973-b795-d68c3cfc73c1' : ComponentPortAllocation
                                allocate allocatedPort ::> 'PP 1'
                                to allocatingPort ::> 'Nose Landing Gear Library'::'Nose Landing Gear'::'Physical Architecture'::'Structure'::'Physical System'.'Behavior Parent'.'Fuel and Power System'.'H2'.'CP 1' { 
                                @CapellaID { eid = "b4c982bd-20c8-4973-b795-d68c3cfc73c1"; } 
                                 
                            }  
                             
                            ref :>> ownedComponentPortAllocations =  ('b4c982bd-20c8-4973-b795-d68c3cfc73c1'); 
                        }  
                        port 'PP 2' : PhysicalPort { 
                            @CapellaID { eid = "e3703758-574c-490c-8caa-56fbbb471bd0"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '789be954-a343-488d-9ecb-31e1291d681a' : ComponentPortAllocation
                                allocate allocatedPort ::> 'PP 2'
                                to allocatingPort ::> 'Nose Landing Gear Library'::'Nose Landing Gear'::'Physical Architecture'::'Structure'::'Physical System'.'Behavior Parent'.'Fuel and Power System'.'H2'.'CP 2' { 
                                @CapellaID { eid = "789be954-a343-488d-9ecb-31e1291d681a"; } 
                                 
                            }  
                             
                            ref :>> ownedComponentPortAllocations =  ('789be954-a343-488d-9ecb-31e1291d681a'); 
                        }  
                         
                    }  
                    part 'H Reservoir' : PhysicalComponent { 
                        @CapellaID { eid = "29bd8398-2f30-4936-be73-59b4e741aec6"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "2fb6d172-554a-4c45-9879-4bf27cbc3cc1"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '087ef925-15ec-484d-ac1a-2b371a82be0f' : ComponentPortAllocation
                                allocate allocatedPort ::> 'PP 1'
                                to allocatingPort ::> 'Nose Landing Gear Library'::'Nose Landing Gear'::'Physical Architecture'::'Structure'::'Physical System'.'Behavior Parent'.'Fuel and Power System'.'H R'.'CP 1' { 
                                @CapellaID { eid = "087ef925-15ec-484d-ac1a-2b371a82be0f"; } 
                                 
                            }  
                             
                            ref :>> ownedComponentPortAllocations =  ('087ef925-15ec-484d-ac1a-2b371a82be0f'); 
                        }  
                        port 'PP 2' : PhysicalPort { 
                            @CapellaID { eid = "0a36a350-9874-469a-bfa5-e5bdf520fbed"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '0f4482ba-a374-4a62-9416-da0597e7bd56' : ComponentPortAllocation
                                allocate allocatedPort ::> 'PP 2'
                                to allocatingPort ::> 'Nose Landing Gear Library'::'Nose Landing Gear'::'Physical Architecture'::'Structure'::'Physical System'.'Behavior Parent'.'Fuel and Power System'.'H R'.'CP 2' { 
                                @CapellaID { eid = "0f4482ba-a374-4a62-9416-da0597e7bd56"; } 
                                 
                            }  
                             
                            ref :>> ownedComponentPortAllocations =  ('0f4482ba-a374-4a62-9416-da0597e7bd56'); 
                        }  
                        port 'PP 3' : PhysicalPort { 
                            @CapellaID { eid = "c0a084f4-ea01-4807-a99f-6670ebe386dd"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation 'bfc5d84c-f879-4561-ae31-2fe0ad8ef53c' : ComponentPortAllocation
                                allocate allocatedPort ::> 'PP 3'
                                to allocatingPort ::> 'Nose Landing Gear Library'::'Nose Landing Gear'::'Physical Architecture'::'Structure'::'Physical System'.'Behavior Parent'.'Fuel and Power System'.'H R'.'CP 3' { 
                                @CapellaID { eid = "bfc5d84c-f879-4561-ae31-2fe0ad8ef53c"; } 
                                 
                            }  
                             
                            ref :>> ownedComponentPortAllocations =  ('bfc5d84c-f879-4561-ae31-2fe0ad8ef53c'); 
                        }  
                        port 'PP 4' : PhysicalPort { 
                            @CapellaID { eid = "9df8aae1-fd5a-4efe-96d4-6dedc559daef"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation 'bff61340-df0d-491d-8b11-7f8fb66591e3' : ComponentPortAllocation
                                allocate allocatedPort ::> 'PP 4'
                                to allocatingPort ::> 'Nose Landing Gear Library'::'Nose Landing Gear'::'Physical Architecture'::'Structure'::'Physical System'.'Behavior Parent'.'Fuel and Power System'.'H R'.'CP 4' { 
                                @CapellaID { eid = "bff61340-df0d-491d-8b11-7f8fb66591e3"; } 
                                 
                            }  
                             
                            ref :>> ownedComponentPortAllocations =  ('bff61340-df0d-491d-8b11-7f8fb66591e3'); 
                        }  
                         
                    }  
                    part 'Pilot Interface' : PhysicalComponent { 
                        @CapellaID { eid = "33a9c3a5-6f1a-4976-adcb-7495b14437f3"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "df01cd26-f700-45f7-a941-23b994927856"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 2' : PhysicalPort { 
                            @CapellaID { eid = "ee2998bf-874b-4664-a224-87823d5c0140"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 3' : PhysicalPort { 
                            @CapellaID { eid = "1ba7d496-52df-478f-b272-e09ae9091f51"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 4' : PhysicalPort { 
                            @CapellaID { eid = "9bfb026e-6a9b-4e54-99f1-73248d2e3038"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 5' : PhysicalPort { 
                            @CapellaID { eid = "cc2621a6-38ec-46a1-9a69-0a750e9f8c6b"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '5c225de1-8d07-472b-8497-33679a8f0d92' : ComponentPortAllocation
                                allocate allocatedPort ::> 'PP 5'
                                to allocatingPort ::> 'Nose Landing Gear Library'::'Nose Landing Gear'::'Physical Architecture'::'Structure'::'Physical System'.'Behavior Parent'.'Fuel and Power System'.'Dump Control'.'CP 3' { 
                                @CapellaID { eid = "5c225de1-8d07-472b-8497-33679a8f0d92"; } 
                                 
                            }  
                             
                            ref :>> ownedComponentPortAllocations =  ('5c225de1-8d07-472b-8497-33679a8f0d92'); 
                        }  
                        port 'PP 6' : PhysicalPort { 
                            @CapellaID { eid = "a3f8eb98-0ff5-43bb-b31f-ac263ec9b795"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation 'f9743360-a6f2-420b-94dc-5bee1e3df753' : ComponentPortAllocation
                                allocate allocatedPort ::> 'PP 6'
                                to allocatingPort ::> 'Nose Landing Gear Library'::'Nose Landing Gear'::'Physical Architecture'::'Structure'::'Physical System'.'Behavior Parent'.'Fuel and Power System'.'Dump Control'.'CP 4' { 
                                @CapellaID { eid = "f9743360-a6f2-420b-94dc-5bee1e3df753"; } 
                                 
                            }  
                             
                            ref :>> ownedComponentPortAllocations =  ('f9743360-a6f2-420b-94dc-5bee1e3df753'); 
                        }  
                         
                    }  
                    part 'NLG Dump Valve' : PhysicalComponent { 
                        @CapellaID { eid = "c5b2b8c6-3a39-4fac-8ee3-691945103eed"; sid = "c5b2b8c6-3a39-4fac-8ee3-691945103eed"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "fe58b66e-5a92-4cb3-b918-b58c39123e61"; sid = "fe58b66e-5a92-4cb3-b918-b58c39123e61"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 2' : PhysicalPort { 
                            @CapellaID { eid = "9c44be19-fa99-4260-a59f-c0544f4c8527"; sid = "9c44be19-fa99-4260-a59f-c0544f4c8527"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 3' : PhysicalPort { 
                            @CapellaID { eid = "2ee576ab-aa80-4c11-ad8b-7d2f2095b62f"; sid = "2ee576ab-aa80-4c11-ad8b-7d2f2095b62f"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 4' : PhysicalPort { 
                            @CapellaID { eid = "6b07a90c-c49d-4770-a326-d54151ad9204"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '6a465af8-afb7-4b88-8d4f-e50a4f0eb72a' : ComponentPortAllocation
                                allocate allocatedPort ::> 'PP 4'
                                to allocatingPort ::> 'Nose Landing Gear Library'::'Nose Landing Gear'::'Physical Architecture'::'Structure'::'Physical System'.'Behavior Parent'.'NLG Dump Valve'.'CP 1' { 
                                @CapellaID { eid = "6a465af8-afb7-4b88-8d4f-e50a4f0eb72a"; } 
                                 
                            }  
                             
                            ref :>> ownedComponentPortAllocations =  ('6a465af8-afb7-4b88-8d4f-e50a4f0eb72a'); 
                        }  
                        port 'PP 5' : PhysicalPort { 
                            @CapellaID { eid = "5da2f701-9e4c-4411-b17e-cc6b7bc550a4"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation 'b9af857e-a60c-4516-921c-c5390645dc8f' : ComponentPortAllocation
                                allocate allocatedPort ::> 'PP 5'
                                to allocatingPort ::> 'Nose Landing Gear Library'::'Nose Landing Gear'::'Physical Architecture'::'Structure'::'Physical System'.'Behavior Parent'.'NLG Dump Valve'.'CP 3' { 
                                @CapellaID { eid = "b9af857e-a60c-4516-921c-c5390645dc8f"; } 
                                 
                            }  
                             
                            ref :>> ownedComponentPortAllocations =  ('b9af857e-a60c-4516-921c-c5390645dc8f'); 
                        }  
                        port 'PP 6' : PhysicalPort { 
                            @CapellaID { eid = "fd1f682a-2895-4d95-ac26-9b0a694e4b03"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '906d01c3-f110-4bd5-8f4c-b078a04d1458' : ComponentPortAllocation
                                allocate allocatedPort ::> 'PP 6'
                                to allocatingPort ::> 'Nose Landing Gear Library'::'Nose Landing Gear'::'Physical Architecture'::'Structure'::'Physical System'.'Behavior Parent'.'NLG Dump Valve'.'CP 2' { 
                                @CapellaID { eid = "906d01c3-f110-4bd5-8f4c-b078a04d1458"; } 
                                 
                            }  
                             
                            ref :>> ownedComponentPortAllocations =  ('906d01c3-f110-4bd5-8f4c-b078a04d1458'); 
                        }  
                         
                    }  
                    part 'ion ' : PhysicalComponent { 
                        @CapellaID { eid = "b036cde3-b432-45db-95d9-5d12be408a3b"; sid = "b036cde3-b432-45db-95d9-5d12be408a3b"; } 
                        attribute :>> isAbstract = false; 
                        attribute :>> isActor = false; 
                        attribute :>> isHuman = false; 
                        attribute :>> kind = PhysicalComponentKind::UNSET; 
                        attribute :>> nature = PhysicalComponentNature::NODE; 
                        port 'PP 1' : PhysicalPort { 
                            @CapellaID { eid = "d4ea69b9-697a-41fa-aa10-b004a541870b"; sid = "d4ea69b9-697a-41fa-aa10-b004a541870b"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '5db9c42e-96e2-4e9f-a2e5-a31cfb83932b' : ComponentPortAllocation
                                allocate allocatedPort ::> 'PP 1'
                                to allocatingPort ::> 'Nose Landing Gear Library'::'Nose Landing Gear'::'Physical Architecture'::'Structure'::'Physical System'.'Behavior Parent'.'NLG  Control Valve'.'CP 2' { 
                                @CapellaID { eid = "5db9c42e-96e2-4e9f-a2e5-a31cfb83932b"; } 
                                 
                            }  
                             
                            ref :>> ownedComponentPortAllocations =  ('5db9c42e-96e2-4e9f-a2e5-a31cfb83932b'); 
                        }  
                        port 'PP 2' : PhysicalPort { 
                            @CapellaID { eid = "9ac135e0-4b30-4811-b532-cc2a6301c3eb"; sid = "9ac135e0-4b30-4811-b532-cc2a6301c3eb"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '6c81d9ad-0445-4d9f-897e-3fbbefec9ed6' : ComponentPortAllocation
                                allocate allocatedPort ::> 'PP 2'
                                to allocatingPort ::> 'Nose Landing Gear Library'::'Nose Landing Gear'::'Physical Architecture'::'Structure'::'Physical System'.'Behavior Parent'.'NLG  Control Valve'.'CP 3' { 
                                @CapellaID { eid = "6c81d9ad-0445-4d9f-897e-3fbbefec9ed6"; } 
                                 
                            }  
                             
                            ref :>> ownedComponentPortAllocations =  ('6c81d9ad-0445-4d9f-897e-3fbbefec9ed6'); 
                        }  
                        port 'PP 3' : PhysicalPort { 
                            @CapellaID { eid = "fe291d62-92ce-40fd-89b7-b169c6ecc2a7"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 4' : PhysicalPort { 
                            @CapellaID { eid = "2f9d8973-e403-400a-a5a5-115def35533c"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        port 'PP 5' : PhysicalPort { 
                            @CapellaID { eid = "b816f9f3-5a1b-4298-bf79-2c20d05b2a9b"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation 'a6b71d8d-ea5e-46ae-a1e5-00a2b13f2551' : ComponentPortAllocation
                                allocate allocatedPort ::> 'PP 5'
                                to allocatingPort ::> 'Nose Landing Gear Library'::'Nose Landing Gear'::'Physical Architecture'::'Structure'::'Physical System'.'Behavior Parent'.'NLG  Control Valve'.'CP 4' { 
                                @CapellaID { eid = "a6b71d8d-ea5e-46ae-a1e5-00a2b13f2551"; } 
                                 
                            }  
                             
                            ref :>> ownedComponentPortAllocations =  ('a6b71d8d-ea5e-46ae-a1e5-00a2b13f2551'); 
                        }  
                         
                    }  
                    part 'Behavior Parent' : PhysicalComponent { 
                        @CapellaID { eid = "cc50f5fd-d13c-4d81-a8c3-450ccc476426"; } 
                        attribute :>> isAbstract = false; 
                        attribute :>> isActor = false; 
                        attribute :>> isHuman = false; 
                        attribute :>> kind = PhysicalComponentKind::UNSET; 
                        attribute :>> nature = PhysicalComponentNature::BEHAVIOR; 
                        interface 'eab01e10-827a-421a-98fc-6aec6317df4f' : ComponentExchange 
                            connect source ::> 'H3'.'CP 1'
                            to  target ::> 'Pressured Hydraulic'.'CP 1' { 
                            @CapellaID { eid = "eab01e10-827a-421a-98fc-6aec6317df4f"; } 
                            attribute :>> kind = ComponentExchangeKind::FLOW; 
                            attribute :>> interfaceName = "H3 to Pressured Hydraulic"; 
                            attribute :>> isOriented = false; 
                            allocation '98e30f20-b162-4798-acfc-596156930709' : ComponentExchangeFunctionalExchangeAllocation
                                allocate functionalExchange ::> 'Physical Functions'::'Root Physical Function'.'41b60723-f7c9-414c-9e34-2b50804b839b'
                                to componentExchange ::> 'eab01e10-827a-421a-98fc-6aec6317df4f' { 
                                @CapellaID { eid = "98e30f20-b162-4798-acfc-596156930709"; } 
                                 
                            }  
                             
                            ref :>> ownedComponentExchangeFunctionalExchangeAllocations =  ('98e30f20-b162-4798-acfc-596156930709'); 
                        }  
                        interface '3da72adf-d20a-4740-a964-39f4bc413126' : ComponentExchange 
                            connect source ::> 'H3'.'CP 2'
                            to  target ::> 'Fuel and Power System'.'H2'.'CP 2' { 
                            @CapellaID { eid = "3da72adf-d20a-4740-a964-39f4bc413126"; } 
                            attribute :>> kind = ComponentExchangeKind::FLOW; 
                            attribute :>> interfaceName = "H3 to H2"; 
                            attribute :>> isOriented = false; 
                            allocation '2dbfc754-01ba-492d-8c48-956c319afb53' : ComponentExchangeFunctionalExchangeAllocation
                                allocate functionalExchange ::> 'Physical Functions'::'Root Physical Function'.'6224d738-93ed-415c-967f-5e125cf75016'
                                to componentExchange ::> '3da72adf-d20a-4740-a964-39f4bc413126' { 
                                @CapellaID { eid = "2dbfc754-01ba-492d-8c48-956c319afb53"; } 
                                 
                            }  
                             
                            ref :>> ownedComponentExchangeFunctionalExchangeAllocations =  ('2dbfc754-01ba-492d-8c48-956c319afb53'); 
                        }  
                        interface 'c65b09b3-88ac-4f59-ba01-e2dfbd98092f' : ComponentExchange 
                            connect source ::> 'Fuel and Power System'.'H R'.'CP 3'
                            to  target ::> 'H3'.'CP 3' { 
                            @CapellaID { eid = "c65b09b3-88ac-4f59-ba01-e2dfbd98092f"; } 
                            attribute :>> kind = ComponentExchangeKind::FLOW; 
                            attribute :>> interfaceName = "H Reservoir to H3"; 
                            attribute :>> isOriented = false; 
                            allocation 'df5497d7-3b8a-4234-a801-38f4f692628b' : ComponentExchangeFunctionalExchangeAllocation
                                allocate functionalExchange ::> 'Physical Functions'::'Root Physical Function'.'dbc3f5d5-2f48-4593-af18-e7139be3d59a'
                                to componentExchange ::> 'c65b09b3-88ac-4f59-ba01-e2dfbd98092f' { 
                                @CapellaID { eid = "df5497d7-3b8a-4234-a801-38f4f692628b"; } 
                                 
                            }  
                             
                            ref :>> ownedComponentExchangeFunctionalExchangeAllocations =  ('df5497d7-3b8a-4234-a801-38f4f692628b'); 
                        }  
                        interface 'f024d824-6d61-4ea2-bd4a-f756f0ca019e' : ComponentExchange 
                            connect source ::> 'Pressured Hydraulic'.'CP 2'
                            to  target ::> 'NLG  Control Valve'.'CP 3' { 
                            @CapellaID { eid = "f024d824-6d61-4ea2-bd4a-f756f0ca019e"; } 
                            attribute :>> kind = ComponentExchangeKind::FLOW; 
                            attribute :>> interfaceName = "Pressured Hydraulic to NLG Control Valve"; 
                            attribute :>> isOriented = false; 
                            allocation 'a0ab97c6-a223-456b-b327-bbfe18e28a74' : ComponentExchangeFunctionalExchangeAllocation
                                allocate functionalExchange ::> 'Physical Functions'::'Root Physical Function'.'59428dfe-81b6-4d97-8654-c1d4bfb73819'
                                to componentExchange ::> 'f024d824-6d61-4ea2-bd4a-f756f0ca019e' { 
                                @CapellaID { eid = "a0ab97c6-a223-456b-b327-bbfe18e28a74"; } 
                                 
                            }  
                             
                            ref :>> ownedComponentExchangeFunctionalExchangeAllocations =  ('a0ab97c6-a223-456b-b327-bbfe18e28a74'); 
                        }  
                        interface '7ea77cc3-28bc-4e03-8364-e9ca89d9083e' : ComponentExchange 
                            connect source ::> 'NLG Dump Valve'.'CP 2'
                            to  target ::> 'Fuel and Power System'.'H R'.'CP 4' { 
                            @CapellaID { eid = "7ea77cc3-28bc-4e03-8364-e9ca89d9083e"; } 
                            attribute :>> kind = ComponentExchangeKind::FLOW; 
                            attribute :>> interfaceName = "NLG Dump Valve to H Reservoir"; 
                            attribute :>> isOriented = false; 
                            allocation 'd1d75442-d548-41a8-8925-ae84320244f7' : ComponentExchangeFunctionalExchangeAllocation
                                allocate functionalExchange ::> 'Physical Functions'::'Root Physical Function'.'3a359c3c-a4a2-411a-8961-29a1bfbea4c6'
                                to componentExchange ::> '7ea77cc3-28bc-4e03-8364-e9ca89d9083e' { 
                                @CapellaID { eid = "d1d75442-d548-41a8-8925-ae84320244f7"; } 
                                 
                            }  
                             
                            ref :>> ownedComponentExchangeFunctionalExchangeAllocations =  ('d1d75442-d548-41a8-8925-ae84320244f7'); 
                        }  
                        interface 'c3caa067-07c8-4ac3-a5b8-7cd31d9cc04b' : ComponentExchange 
                            connect source ::> 'NLG  Control Valve'.'CP 4'
                            to  target ::> 'NLG Dump Valve'.'CP 3' { 
                            @CapellaID { eid = "c3caa067-07c8-4ac3-a5b8-7cd31d9cc04b"; } 
                            attribute :>> kind = ComponentExchangeKind::FLOW; 
                            attribute :>> interfaceName = "NLG Control Valve to NLG Dump Valve"; 
                            attribute :>> isOriented = false; 
                            allocation '8395239d-6112-4c3c-9cf8-550b696b6213' : ComponentExchangeFunctionalExchangeAllocation
                                allocate functionalExchange ::> 'Physical Functions'::'Root Physical Function'.'a6323585-d7fe-48a4-9fd2-6c73636ff52d'
                                to componentExchange ::> 'c3caa067-07c8-4ac3-a5b8-7cd31d9cc04b' { 
                                @CapellaID { eid = "8395239d-6112-4c3c-9cf8-550b696b6213"; } 
                                 
                            }  
                             
                            ref :>> ownedComponentExchangeFunctionalExchangeAllocations =  ('8395239d-6112-4c3c-9cf8-550b696b6213'); 
                        }  
                        interface '9d144b9e-1cd2-440b-a540-60b7a99884a2' : ComponentExchange 
                            connect source ::> 'Pressured Hydraulic'.'CP 3'
                            to  target ::> 'NLG Doors Selector Valve'.'CP 4' { 
                            @CapellaID { eid = "9d144b9e-1cd2-440b-a540-60b7a99884a2"; } 
                            attribute :>> kind = ComponentExchangeKind::FLOW; 
                            attribute :>> interfaceName = "Pressured Hydraulic to NLG Doors Selector Valve"; 
                            attribute :>> isOriented = false; 
                            allocation '0ce3d30d-56a3-4129-9b46-b96ee24b4c81' : ComponentExchangeFunctionalExchangeAllocation
                                allocate functionalExchange ::> 'Physical Functions'::'Root Physical Function'.'58b22acb-b13f-4000-bdf5-222a6006c90c'
                                to componentExchange ::> '9d144b9e-1cd2-440b-a540-60b7a99884a2' { 
                                @CapellaID { eid = "0ce3d30d-56a3-4129-9b46-b96ee24b4c81"; } 
                                 
                            }  
                             
                            ref :>> ownedComponentExchangeFunctionalExchangeAllocations =  ('0ce3d30d-56a3-4129-9b46-b96ee24b4c81'); 
                        }  
                        part '749bbb13-35c4-45d4-a813-c3e0536fd141' : CPart :> 'NLG Wheel'  { 
                            @CapellaID { eid = "749bbb13-35c4-45d4-a813-c3e0536fd141"; sid = "749bbb13-35c4-45d4-a813-c3e0536fd141"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '26ce5afc-104f-4b53-8dcd-4e427b97ab8a' : CPart :> 'NLG Dump Valve'  { 
                            @CapellaID { eid = "26ce5afc-104f-4b53-8dcd-4e427b97ab8a"; sid = "26ce5afc-104f-4b53-8dcd-4e427b97ab8a"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'd75405ec-e7b7-4a9d-86ed-f888d7af4602' : CPart :> 'Airframe'  { 
                            @CapellaID { eid = "d75405ec-e7b7-4a9d-86ed-f888d7af4602"; sid = "d75405ec-e7b7-4a9d-86ed-f888d7af4602"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'e1acfc99-c49f-4f2a-8688-38c5f4fe8d8a' : CPart :> 'NLG Doors Dump Valve'  { 
                            @CapellaID { eid = "e1acfc99-c49f-4f2a-8688-38c5f4fe8d8a"; sid = "e1acfc99-c49f-4f2a-8688-38c5f4fe8d8a"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'ece32dd0-24f7-461d-aaa6-37c034d46293' : CPart :> 'NLG Uplock Sensor 2'  { 
                            @CapellaID { eid = "ece32dd0-24f7-461d-aaa6-37c034d46293"; sid = "ece32dd0-24f7-461d-aaa6-37c034d46293"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'cd969767-4080-46b2-9b0b-35ad6fa4b92d' : CPart :> 'NLG Wheel Steerin'  { 
                            @CapellaID { eid = "cd969767-4080-46b2-9b0b-35ad6fa4b92d"; sid = "cd969767-4080-46b2-9b0b-35ad6fa4b92d"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'b8f45b4b-30d6-4f43-be5f-6a3777f05763' : CPart :> 'NLG Shock'  { 
                            @CapellaID { eid = "b8f45b4b-30d6-4f43-be5f-6a3777f05763"; sid = "b8f45b4b-30d6-4f43-be5f-6a3777f05763"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '75cb0d7a-cebb-4b7e-8a82-79d68ac11430' : CPart :> 'Weight on Wheelp Sensor 2'  { 
                            @CapellaID { eid = "75cb0d7a-cebb-4b7e-8a82-79d68ac11430"; sid = "75cb0d7a-cebb-4b7e-8a82-79d68ac11430"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'bf33130a-0fb5-476b-90fe-009b09618fdf' : CPart :> 'NLG Struct Post'  { 
                            @CapellaID { eid = "bf33130a-0fb5-476b-90fe-009b09618fdf"; sid = "bf33130a-0fb5-476b-90fe-009b09618fdf"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '50c7b57a-d789-4f03-9a43-10cf58c245bd' : CPart :> 'NLG Downlock Sensor 1'  { 
                            @CapellaID { eid = "50c7b57a-d789-4f03-9a43-10cf58c245bd"; sid = "50c7b57a-d789-4f03-9a43-10cf58c245bd"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '2c5933bc-4f77-4bd2-830f-ef8a4b15ab79' : CPart :> 'NLG Downlock Sensor 2'  { 
                            @CapellaID { eid = "2c5933bc-4f77-4bd2-830f-ef8a4b15ab79"; sid = "2c5933bc-4f77-4bd2-830f-ef8a4b15ab79"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'd4d60991-ba83-4b37-a894-6c1299572d0a' : CPart :> 'NLG Uplock Sensor 1'  { 
                            @CapellaID { eid = "d4d60991-ba83-4b37-a894-6c1299572d0a"; sid = "d4d60991-ba83-4b37-a894-6c1299572d0a"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '64e734de-28ee-410a-a736-4b8fe959847e' : CPart :> 'Weight on Wheel Sensor 1'  { 
                            @CapellaID { eid = "64e734de-28ee-410a-a736-4b8fe959847e"; sid = "64e734de-28ee-410a-a736-4b8fe959847e"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '5c405984-5543-4f5a-ae8f-5761417aa328' : CPart :> 'NLG Doors Selector Valve'  { 
                            @CapellaID { eid = "5c405984-5543-4f5a-ae8f-5761417aa328"; sid = "5c405984-5543-4f5a-ae8f-5761417aa328"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'da1e3920-5a9a-463a-add6-97969bbe19d1' : CPart :> 'NLG  Control Valve'  { 
                            @CapellaID { eid = "da1e3920-5a9a-463a-add6-97969bbe19d1"; sid = "da1e3920-5a9a-463a-add6-97969bbe19d1"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '40d3799b-932a-437e-aa46-9a6602e38fa9' : CPart :> 'NLG Door Actuator'  { 
                            @CapellaID { eid = "40d3799b-932a-437e-aa46-9a6602e38fa9"; sid = "40d3799b-932a-437e-aa46-9a6602e38fa9"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '964d5412-c1e7-43cd-8e48-9dc72148801b' : CPart :> 'NLG Door Sensor'  { 
                            @CapellaID { eid = "964d5412-c1e7-43cd-8e48-9dc72148801b"; sid = "964d5412-c1e7-43cd-8e48-9dc72148801b"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '1b07bf32-e720-435e-b7f1-613b66e56098' : CPart :> 'Shutoff Valve'  { 
                            @CapellaID { eid = "1b07bf32-e720-435e-b7f1-613b66e56098"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '7351d56a-1d18-47d4-8545-7082891ecee8' : CPart :> 'Isolation Valve'  { 
                            @CapellaID { eid = "7351d56a-1d18-47d4-8545-7082891ecee8"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'f936ab29-48bc-4d9e-8fde-e2a35baedfe4' : CPart :> 'Blue Hydraulic Pump'  { 
                            @CapellaID { eid = "f936ab29-48bc-4d9e-8fde-e2a35baedfe4"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '2ab53a75-5e83-49ac-a1ec-aaac190cc8c0' : CPart :> 'Pressured Hydraulic'  { 
                            @CapellaID { eid = "2ab53a75-5e83-49ac-a1ec-aaac190cc8c0"; sid = "2ab53a75-5e83-49ac-a1ec-aaac190cc8c0"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '5af834d3-aba6-444b-af4f-37795ca5c9ec' : CPart :> 'Extension Retraction Lever'  { 
                            @CapellaID { eid = "5af834d3-aba6-444b-af4f-37795ca5c9ec"; sid = "5af834d3-aba6-444b-af4f-37795ca5c9ec"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'd7343dea-ffd1-40c7-9aa8-3763cfc7f43b' : CPart :> 'NLG'  { 
                            @CapellaID { eid = "d7343dea-ffd1-40c7-9aa8-3763cfc7f43b"; sid = "d7343dea-ffd1-40c7-9aa8-3763cfc7f43b"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '27e6a2fc-6333-416b-8605-0293d9ff16a7' : CPart :> 'HR'  { 
                            @CapellaID { eid = "27e6a2fc-6333-416b-8605-0293d9ff16a7"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '49713b75-2374-424c-8288-3a62dc79a3f5' : CPart :> 'PC 40'  { 
                            @CapellaID { eid = "49713b75-2374-424c-8288-3a62dc79a3f5"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'd0f0f69b-337d-436e-bbcb-ffa9b124bf5b' : CPart :> 'H3'  { 
                            @CapellaID { eid = "d0f0f69b-337d-436e-bbcb-ffa9b124bf5b"; sid = "d0f0f69b-337d-436e-bbcb-ffa9b124bf5b"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'fbe0c0b0-6bd7-466f-9c66-503dc3034368' : CPart :> 'Fuel and Power System'  { 
                            @CapellaID { eid = "fbe0c0b0-6bd7-466f-9c66-503dc3034368"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part '8ceab8e5-ef83-4b89-b7a6-0926940807dd' : CPart :> 'ComLink'  { 
                            @CapellaID { eid = "8ceab8e5-ef83-4b89-b7a6-0926940807dd"; sid = "8ceab8e5-ef83-4b89-b7a6-0926940807dd"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                             
                        }  
                        part 'NLG Downlock Sensor 2' : PhysicalComponent { 
                            @CapellaID { eid = "9b4305c0-2efb-426d-975a-30b2fc061001"; sid = "9b4305c0-2efb-426d-975a-30b2fc061001"; } 
                            attribute :>> isAbstract = false; 
                            attribute :>> isActor = false; 
                            attribute :>> isHuman = false; 
                            attribute :>> kind = PhysicalComponentKind::UNSET; 
                            attribute :>> nature = PhysicalComponentNature::BEHAVIOR; 
                            allocation 'bb32be8e-a5ca-462f-a24c-3e5142c873b8' : ComponentFunctionalAllocation
                                allocate function ::> 'Physical Functions'::'Root Physical Function'.'Sense Hardware'.'Sense DWNLock Position 2'
                                to component ::> 'NLG Downlock Sensor 2' { 
                                @CapellaID { eid = "bb32be8e-a5ca-462f-a24c-3e5142c873b8"; } 
                                 
                            } 
                            perform 'Physical Functions'::'Root Physical Function'.'Sense Hardware'.'Sense DWNLock Position 2' ; 
                            port 'CP 1' : ComponentPort { 
                                @CapellaID { eid = "75cc461f-dbf6-42e8-9ae0-226f780f3e8e"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '91c50ceb-515d-4c58-9cef-a05937d026bc' : PortAllocation
                                    allocate allocatedPort ::> 'Physical Functions'::'Root Physical Function'.'Sense Hardware'.'Sense DWNLock Position 2'.'FOP 3'
                                    to allocatingPort ::> 'CP 1'; 
                                ref :>> ownedPortAllocations =  ('91c50ceb-515d-4c58-9cef-a05937d026bc'); 
                                 
                            }  
                            ref :>> ownedFunctionalAllocation =  ('bb32be8e-a5ca-462f-a24c-3e5142c873b8'); 
                             
                        }  
                        part 'NLG Dump Valve' : PhysicalComponent { 
                            @CapellaID { eid = "7196e099-ed07-4b5e-8f62-e240aaf1b491"; sid = "7196e099-ed07-4b5e-8f62-e240aaf1b491"; } 
                            attribute :>> isAbstract = false; 
                            attribute :>> isActor = false; 
                            attribute :>> isHuman = false; 
                            attribute :>> kind = PhysicalComponentKind::UNSET; 
                            attribute :>> nature = PhysicalComponentNature::BEHAVIOR; 
                            allocation '2d5b0fd3-b5df-4269-a007-f7d72eab5ee7' : ComponentFunctionalAllocation
                                allocate function ::> 'Physical Functions'::'Root Physical Function'.'Release Selector Valve Pressure'
                                to component ::> 'NLG Dump Valve' { 
                                @CapellaID { eid = "2d5b0fd3-b5df-4269-a007-f7d72eab5ee7"; } 
                                 
                            } 
                            perform 'Physical Functions'::'Root Physical Function'.'Release Selector Valve Pressure' ; 
                            port 'CP 1' : ComponentPort { 
                                @CapellaID { eid = "ea991572-fa68-43a8-9fdb-407870bab7c5"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation '66dcdfe8-9574-429a-8d3f-c973c6949a95' : PortAllocation
                                    allocate allocatedPort ::> 'Physical Functions'::'Root Physical Function'.'Release Selector Valve Pressure'.'FIP 2'
                                    to allocatingPort ::> 'CP 1'; 
                                ref :>> ownedPortAllocations =  ('66dcdfe8-9574-429a-8d3f-c973c6949a95'); 
                                 
                            }  
                            port 'CP 2' : ComponentPort { 
                                @CapellaID { eid = "d3e84e28-0072-4eee-845c-fd1c3ce28bc5"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '3766ecb6-1a56-4029-a3c9-5613e5584214' : PortAllocation
                                    allocate allocatedPort ::> 'Physical Functions'::'Root Physical Function'.'Release Selector Valve Pressure'.'FOP 1'
                                    to allocatingPort ::> 'CP 2'; 
                                ref :>> ownedPortAllocations =  ('3766ecb6-1a56-4029-a3c9-5613e5584214'); 
                                 
                            }  
                            port 'CP 3' : ComponentPort { 
                                @CapellaID { eid = "a5c06e14-ca66-4c0e-a007-cf9979c7ea32"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation '664d7176-d2c5-47af-a401-60b6b784a684' : PortAllocation
                                    allocate allocatedPort ::> 'Physical Functions'::'Root Physical Function'.'Release Selector Valve Pressure'.'FIP 1'
                                    to allocatingPort ::> 'CP 3'; 
                                ref :>> ownedPortAllocations =  ('664d7176-d2c5-47af-a401-60b6b784a684'); 
                                 
                            }  
                            ref :>> ownedFunctionalAllocation =  ('2d5b0fd3-b5df-4269-a007-f7d72eab5ee7'); 
                             
                        }  
                        part 'NLG Doors Dump Valve' : PhysicalComponent { 
                            @CapellaID { eid = "949ba149-cf34-416a-b44e-191bed1c685b"; sid = "949ba149-cf34-416a-b44e-191bed1c685b"; } 
                            attribute :>> isAbstract = false; 
                            attribute :>> isActor = false; 
                            attribute :>> isHuman = false; 
                            attribute :>> kind = PhysicalComponentKind::UNSET; 
                            attribute :>> nature = PhysicalComponentNature::BEHAVIOR; 
                            allocation '030daffb-ec78-4ee9-88b8-6e6eca8da57b' : ComponentFunctionalAllocation
                                allocate function ::> 'Physical Functions'::'Root Physical Function'.'Release Door Valve Pressure '
                                to component ::> 'NLG Doors Dump Valve' { 
                                @CapellaID { eid = "030daffb-ec78-4ee9-88b8-6e6eca8da57b"; } 
                                 
                            } 
                            perform 'Physical Functions'::'Root Physical Function'.'Release Door Valve Pressure ' ; 
                            port 'CP 1' : ComponentPort { 
                                @CapellaID { eid = "06a8cac4-079b-49e3-bb81-09b7e71cc982"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation 'bc25563d-fe13-47d5-b9ae-9c75da6ed926' : PortAllocation
                                    allocate allocatedPort ::> 'Physical Functions'::'Root Physical Function'.'Release Door Valve Pressure '.'FIP 2'
                                    to allocatingPort ::> 'CP 1'; 
                                ref :>> ownedPortAllocations =  ('bc25563d-fe13-47d5-b9ae-9c75da6ed926'); 
                                 
                            }  
                            port 'CP 2' : ComponentPort { 
                                @CapellaID { eid = "dbbafb2a-044b-40bb-981d-722e9386ff0b"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '6b171cc4-9348-4b7c-b45d-67ab8a154014' : PortAllocation
                                    allocate allocatedPort ::> 'Physical Functions'::'Root Physical Function'.'Release Door Valve Pressure '.'FIP 1'
                                    to allocatingPort ::> 'CP 2'; 
                                ref :>> ownedPortAllocations =  ('6b171cc4-9348-4b7c-b45d-67ab8a154014'); 
                                 
                            }  
                            port 'CP 3' : ComponentPort { 
                                @CapellaID { eid = "c87846e0-95b5-44eb-985a-5151cd60d794"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation 'd0710579-8a28-4b20-ad92-484e17df2fc6' : PortAllocation
                                    allocate allocatedPort ::> 'Physical Functions'::'Root Physical Function'.'Release Door Valve Pressure '.'FOP 1'
                                    to allocatingPort ::> 'CP 3'; 
                                ref :>> ownedPortAllocations =  ('d0710579-8a28-4b20-ad92-484e17df2fc6'); 
                                 
                            }  
                            ref :>> ownedFunctionalAllocation =  ('030daffb-ec78-4ee9-88b8-6e6eca8da57b'); 
                             
                        }  
                        part 'Weight on Wheel Sensor 1' : PhysicalComponent { 
                            @CapellaID { eid = "e6b1f4cd-11fb-4cd2-b351-f4f4557d0e9d"; sid = "e6b1f4cd-11fb-4cd2-b351-f4f4557d0e9d"; } 
                            attribute :>> isAbstract = false; 
                            attribute :>> isActor = false; 
                            attribute :>> isHuman = false; 
                            attribute :>> kind = PhysicalComponentKind::UNSET; 
                            attribute :>> nature = PhysicalComponentNature::BEHAVIOR; 
                            allocation '7b132915-7dd3-4725-bbb9-ec4e7512e1f1' : ComponentFunctionalAllocation
                                allocate function ::> 'Physical Functions'::'Root Physical Function'.'Sense Weight on Wheels'
                                to component ::> 'Weight on Wheel Sensor 1' { 
                                @CapellaID { eid = "7b132915-7dd3-4725-bbb9-ec4e7512e1f1"; } 
                                 
                            } 
                            perform 'Physical Functions'::'Root Physical Function'.'Sense Weight on Wheels' ; 
                            port 'CP 1' : ComponentPort { 
                                @CapellaID { eid = "47466735-c264-4fa3-882c-5e28082536b6"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation 'f3272849-476a-4160-9769-137882b69f04' : PortAllocation
                                    allocate allocatedPort ::> 'Physical Functions'::'Root Physical Function'.'Sense Weight on Wheels'.'FOP 1'
                                    to allocatingPort ::> 'CP 1'; 
                                ref :>> ownedPortAllocations =  ('f3272849-476a-4160-9769-137882b69f04'); 
                                 
                            }  
                            ref :>> ownedFunctionalAllocation =  ('7b132915-7dd3-4725-bbb9-ec4e7512e1f1'); 
                             
                        }  
                        part 'NLG Wheel Steerin' : PhysicalComponent { 
                            @CapellaID { eid = "26e9d349-6a8f-4f94-8156-7864fd25597e"; sid = "26e9d349-6a8f-4f94-8156-7864fd25597e"; } 
                            attribute :>> isAbstract = false; 
                            attribute :>> isActor = false; 
                            attribute :>> isHuman = false; 
                            attribute :>> kind = PhysicalComponentKind::UNSET; 
                            attribute :>> nature = PhysicalComponentNature::BEHAVIOR; 
                            allocation '741d807f-ce94-4578-8256-f52fbd5525fd' : ComponentFunctionalAllocation
                                allocate function ::> 'Physical Functions'::'Root Physical Function'.'Measure'.'Actuate NLG'.'Move Gea Up Down'
                                to component ::> 'NLG Wheel Steerin' { 
                                @CapellaID { eid = "741d807f-ce94-4578-8256-f52fbd5525fd"; sid = "741d807f-ce94-4578-8256-f52fbd5525fd"; } 
                                 
                            } 
                            perform 'Physical Functions'::'Root Physical Function'.'Measure'.'Actuate NLG'.'Move Gea Up Down' ; 
                            port 'CP 1' : ComponentPort { 
                                @CapellaID { eid = "2514b603-a09c-4fe8-9a67-7a99fbdd989d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation 'aafe3955-ada8-40b5-a9fc-e947b1aee5d1' : PortAllocation
                                    allocate allocatedPort ::> 'Physical Functions'::'Root Physical Function'.'Measure'.'Actuate NLG'.'Move Gea Up Down'.'FIP 1'
                                    to allocatingPort ::> 'CP 1'; 
                                ref :>> ownedPortAllocations =  ('aafe3955-ada8-40b5-a9fc-e947b1aee5d1'); 
                                 
                            }  
                            port 'CP 2' : ComponentPort { 
                                @CapellaID { eid = "4e20e7cf-7e15-4129-ac70-dceba4c4ea93"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation 'c08a8fd1-9c96-49d3-83f0-0d385ad3857a' : PortAllocation
                                    allocate allocatedPort ::> 'Physical Functions'::'Root Physical Function'.'Measure'.'Actuate NLG'.'Move Gea Up Down'.'FOP 1'
                                    to allocatingPort ::> 'CP 2'; 
                                ref :>> ownedPortAllocations =  ('c08a8fd1-9c96-49d3-83f0-0d385ad3857a'); 
                                 
                            }  
                            ref :>> ownedFunctionalAllocation =  ('741d807f-ce94-4578-8256-f52fbd5525fd'); 
                             
                        }  
                        part 'NLG Uplock Sensor 1' : PhysicalComponent { 
                            @CapellaID { eid = "ff6e49f3-c850-428f-a663-7138d97699c7"; sid = "ff6e49f3-c850-428f-a663-7138d97699c7"; } 
                            attribute :>> isAbstract = false; 
                            attribute :>> isActor = false; 
                            attribute :>> isHuman = false; 
                            attribute :>> kind = PhysicalComponentKind::UNSET; 
                            attribute :>> nature = PhysicalComponentNature::BEHAVIOR; 
                            allocation '559703e9-ccbf-4213-877c-ab7dbe0e24a0' : ComponentFunctionalAllocation
                                allocate function ::> 'Physical Functions'::'Root Physical Function'.'Sense Hardware'.'Sense NLG Uplock Position 1'
                                to component ::> 'NLG Uplock Sensor 1' { 
                                @CapellaID { eid = "559703e9-ccbf-4213-877c-ab7dbe0e24a0"; } 
                                 
                            } 
                            perform 'Physical Functions'::'Root Physical Function'.'Sense Hardware'.'Sense NLG Uplock Position 1' ; 
                            port 'CP 1' : ComponentPort { 
                                @CapellaID { eid = "150a5c7c-60fb-4e0e-9681-9834747e9056"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation 'ce478ec1-1aef-4170-bcce-9c44fe32ee82' : PortAllocation
                                    allocate allocatedPort ::> 'Physical Functions'::'Root Physical Function'.'Sense Hardware'.'Sense NLG Uplock Position 1'.'FOP 4'
                                    to allocatingPort ::> 'CP 1'; 
                                ref :>> ownedPortAllocations =  ('ce478ec1-1aef-4170-bcce-9c44fe32ee82'); 
                                 
                            }  
                            ref :>> ownedFunctionalAllocation =  ('559703e9-ccbf-4213-877c-ab7dbe0e24a0'); 
                             
                        }  
                        part 'NLG Door Actuator' : PhysicalComponent { 
                            @CapellaID { eid = "1a963639-f7e9-4022-aa22-d8b0daf42b9d"; sid = "1a963639-f7e9-4022-aa22-d8b0daf42b9d"; } 
                            attribute :>> isAbstract = false; 
                            attribute :>> isActor = false; 
                            attribute :>> isHuman = false; 
                            attribute :>> kind = PhysicalComponentKind::UNSET; 
                            attribute :>> nature = PhysicalComponentNature::BEHAVIOR; 
                            allocation '79098e3d-bd1e-477d-b876-39db966ee8f5' : ComponentFunctionalAllocation
                                allocate function ::> 'Physical Functions'::'Root Physical Function'.'Move Door'
                                to component ::> 'NLG Door Actuator' { 
                                @CapellaID { eid = "79098e3d-bd1e-477d-b876-39db966ee8f5"; } 
                                 
                            } 
                            perform 'Physical Functions'::'Root Physical Function'.'Move Door' ; 
                            port 'CP 1' : ComponentPort { 
                                @CapellaID { eid = "352313d2-4a1c-4f8c-8cef-c83b17f89d1d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation 'd9dde3a5-7b9d-4804-8366-c94b03dd7cfd' : PortAllocation
                                    allocate allocatedPort ::> 'Physical Functions'::'Root Physical Function'.'Move Door'.'FOP 1'
                                    to allocatingPort ::> 'CP 1'; 
                                ref :>> ownedPortAllocations =  ('d9dde3a5-7b9d-4804-8366-c94b03dd7cfd'); 
                                 
                            }  
                            port 'CP 2' : ComponentPort { 
                                @CapellaID { eid = "fa84ce70-00fc-4cf0-84b9-20bc40e9b7f1"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation 'c2908498-e662-4835-ac27-0f4c5135e536' : PortAllocation
                                    allocate allocatedPort ::> 'Physical Functions'::'Root Physical Function'.'Move Door'.'FIP 1'
                                    to allocatingPort ::> 'CP 2'; 
                                ref :>> ownedPortAllocations =  ('c2908498-e662-4835-ac27-0f4c5135e536'); 
                                 
                            }  
                            ref :>> ownedFunctionalAllocation =  ('79098e3d-bd1e-477d-b876-39db966ee8f5'); 
                             
                        }  
                        part 'NLG Struct Post' : PhysicalComponent { 
                            @CapellaID { eid = "3d662655-29c5-4c6f-8230-92e3118b20d3"; sid = "3d662655-29c5-4c6f-8230-92e3118b20d3"; } 
                            attribute :>> isAbstract = false; 
                            attribute :>> isActor = false; 
                            attribute :>> isHuman = false; 
                            attribute :>> kind = PhysicalComponentKind::UNSET; 
                            attribute :>> nature = PhysicalComponentNature::BEHAVIOR; 
                            allocation 'bd03463b-fd43-446c-949b-7bd49f843596' : ComponentFunctionalAllocation
                                allocate function ::> 'Physical Functions'::'Root Physical Function'.'Transmit NLG Forces'.'Transmit NLG Structural Post'
                                to component ::> 'NLG Struct Post' { 
                                @CapellaID { eid = "bd03463b-fd43-446c-949b-7bd49f843596"; sid = "bd03463b-fd43-446c-949b-7bd49f843596"; } 
                                 
                            } 
                            perform 'Physical Functions'::'Root Physical Function'.'Transmit NLG Forces'.'Transmit NLG Structural Post' ; 
                            port 'CP 1' : ComponentPort { 
                                @CapellaID { eid = "b8e3979a-eb48-4bff-8f47-21532cf1dc8d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '747414ee-a263-4c1b-b9dd-1dd45a696d66' : PortAllocation
                                    allocate allocatedPort ::> 'Physical Functions'::'Root Physical Function'.'Transmit NLG Forces'.'Transmit NLG Structural Post'.'FOP 3'
                                    to allocatingPort ::> 'CP 1'; 
                                ref :>> ownedPortAllocations =  ('747414ee-a263-4c1b-b9dd-1dd45a696d66'); 
                                 
                            }  
                            port 'CP 2' : ComponentPort { 
                                @CapellaID { eid = "51f2dc7c-26b8-48af-82bd-89c06ed10797"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '16f5c6b6-35e8-444f-8434-5c04653064aa' : PortAllocation
                                    allocate allocatedPort ::> 'Physical Functions'::'Root Physical Function'.'Transmit NLG Forces'.'Transmit NLG Structural Post'.'FIP 1'
                                    to allocatingPort ::> 'CP 2'; 
                                ref :>> ownedPortAllocations =  ('16f5c6b6-35e8-444f-8434-5c04653064aa'); 
                                 
                            }  
                            port 'CP 3' : ComponentPort { 
                                @CapellaID { eid = "7727554d-98ae-4bc9-a82d-cc43d32baaef"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation 'c8eb1b73-63da-453b-a6ee-9dda988cc025' : PortAllocation
                                    allocate allocatedPort ::> 'Physical Functions'::'Root Physical Function'.'Transmit NLG Forces'.'Transmit NLG Structural Post'.'FIP 2'
                                    to allocatingPort ::> 'CP 3'; 
                                ref allocation '97f049a4-42c8-4eb1-acf2-ffccafcf2ac1' : PortAllocation
                                    allocate allocatedPort ::> 'Physical Functions'::'Root Physical Function'.'Transmit NLG Forces'.'Transmit NLG Structural Post'.'FIP 3'
                                    to allocatingPort ::> 'CP 3'; 
                                ref :>> ownedPortAllocations =  ('c8eb1b73-63da-453b-a6ee-9dda988cc025',
                                '97f049a4-42c8-4eb1-acf2-ffccafcf2ac1'); 
                                 
                            }  
                            ref :>> ownedFunctionalAllocation =  ('bd03463b-fd43-446c-949b-7bd49f843596'); 
                             
                        }  
                        part 'NLG Door Sensor' : PhysicalComponent { 
                            @CapellaID { eid = "59dd9efb-87c4-486d-8401-ec3d402d2e43"; sid = "59dd9efb-87c4-486d-8401-ec3d402d2e43"; } 
                            attribute :>> isAbstract = false; 
                            attribute :>> isActor = false; 
                            attribute :>> isHuman = false; 
                            attribute :>> kind = PhysicalComponentKind::UNSET; 
                            attribute :>> nature = PhysicalComponentNature::BEHAVIOR; 
                            allocation 'b3ffcbf7-e6fb-430c-abbf-de8525cc33e6' : ComponentFunctionalAllocation
                                allocate function ::> 'Physical Functions'::'Root Physical Function'.'Sense Hardware'.'Sense NLG Door Position'
                                to component ::> 'NLG Door Sensor' { 
                                @CapellaID { eid = "b3ffcbf7-e6fb-430c-abbf-de8525cc33e6"; } 
                                 
                            } 
                            perform 'Physical Functions'::'Root Physical Function'.'Sense Hardware'.'Sense NLG Door Position' ; 
                            port 'CP 1' : ComponentPort { 
                                @CapellaID { eid = "7476c3ec-f77f-4dfc-9932-87c7cabadd12"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                 
                            }  
                            ref :>> ownedFunctionalAllocation =  ('b3ffcbf7-e6fb-430c-abbf-de8525cc33e6'); 
                             
                        }  
                        part 'Airframe' : PhysicalComponent { 
                            @CapellaID { eid = "85871393-7a5d-483a-9009-dbccfbe2f2f1"; sid = "85871393-7a5d-483a-9009-dbccfbe2f2f1"; } 
                            attribute :>> isAbstract = false; 
                            attribute :>> isActor = false; 
                            attribute :>> isHuman = false; 
                            attribute :>> kind = PhysicalComponentKind::UNSET; 
                            attribute :>> nature = PhysicalComponentNature::BEHAVIOR; 
                            dependency '39c8d11f-8698-499a-a3cf-0cdb67ce8326'
                                from '7d28a750-22a8-48a1-beb0-0718b9e67c7e'
                                to  'Logical Architecture'::'Structure'::'UAV System'::'Drone'::'Airframe'::'05b497c4-876e-4fc1-86a8-f724bd86564a' { 
                                @TransfoLink { 
                                    @CapellaID { eid = "39c8d11f-8698-499a-a3cf-0cdb67ce8326"; } 
                                }  
                            }  
                            dependency '9afb49ee-a6f2-4750-b1aa-793ebf23015b'
                                from '9ac6d92b-b4ee-44c7-8937-8eea2d268f20'
                                to  'Logical Architecture'::'Structure'::'UAV System'::'Drone'::'Airframe'::'be6c29aa-5b92-4583-8098-4689dc3607b4' { 
                                @TransfoLink { 
                                    @CapellaID { eid = "9afb49ee-a6f2-4750-b1aa-793ebf23015b"; } 
                                }  
                            }  
                            dependency 'e1c28142-9fd2-4161-aa33-cd3c3c99c623'
                                from 'cba10dc0-2ec1-41ba-b99e-1eb8fe51c61a'
                                to  'Logical Architecture'::'Structure'::'UAV System'::'Drone'::'Airframe'::'3471d182-7507-45d7-9997-141a2e48bba2' { 
                                @TransfoLink { 
                                    @CapellaID { eid = "e1c28142-9fd2-4161-aa33-cd3c3c99c623"; } 
                                }  
                            }  
                            allocation 'adc48c8e-a1b5-499a-ab4c-46476ca23274' : ComponentFunctionalAllocation
                                allocate function ::> 'Physical Functions'::'Root Physical Function'.'Support '
                                to component ::> 'Airframe' { 
                                @CapellaID { eid = "adc48c8e-a1b5-499a-ab4c-46476ca23274"; sid = "adc48c8e-a1b5-499a-ab4c-46476ca23274"; } 
                                 
                            } 
                            perform 'Physical Functions'::'Root Physical Function'.'Support ' ; 
                            allocation '43db8d91-a660-484b-bb3a-ff0e1a6c9a96' : ComponentFunctionalAllocation
                                allocate function ::> 'Physical Functions'::'Root Physical Function'.'Transmit LG Force'
                                to component ::> 'Airframe' { 
                                @CapellaID { eid = "43db8d91-a660-484b-bb3a-ff0e1a6c9a96"; sid = "43db8d91-a660-484b-bb3a-ff0e1a6c9a96"; } 
                                 
                            } 
                            perform 'Physical Functions'::'Root Physical Function'.'Transmit LG Force' ; 
                            allocation '8c5de056-8b14-4c0e-852c-a890c8e797ec' : ComponentFunctionalAllocation
                                allocate function ::> 'Physical Functions'::'Root Physical Function'.'Duplicate 67'
                                to component ::> 'Airframe' { 
                                @CapellaID { eid = "8c5de056-8b14-4c0e-852c-a890c8e797ec"; sid = "8c5de056-8b14-4c0e-852c-a890c8e797ec"; } 
                                 
                            } 
                            perform 'Physical Functions'::'Root Physical Function'.'Duplicate 67' ; 
                            allocation '0f0f6a7a-d683-464b-a6a8-f1df96245c83' : ComponentFunctionalAllocation
                                allocate function ::> 'Physical Functions'::'Root Physical Function'.'Support LG'.'Duplicate 4'
                                to component ::> 'Airframe' { 
                                @CapellaID { eid = "0f0f6a7a-d683-464b-a6a8-f1df96245c83"; sid = "0f0f6a7a-d683-464b-a6a8-f1df96245c83"; } 
                                 
                            } 
                            perform 'Physical Functions'::'Root Physical Function'.'Support LG'.'Duplicate 4' ; 
                            part '7d28a750-22a8-48a1-beb0-0718b9e67c7e' : CPart :> 'Fuselage'  { 
                                @CapellaID { eid = "7d28a750-22a8-48a1-beb0-0718b9e67c7e"; sid = "7d28a750-22a8-48a1-beb0-0718b9e67c7e"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part '9ac6d92b-b4ee-44c7-8937-8eea2d268f20' : CPart :> 'Empennage'  { 
                                @CapellaID { eid = "9ac6d92b-b4ee-44c7-8937-8eea2d268f20"; sid = "9ac6d92b-b4ee-44c7-8937-8eea2d268f20"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part 'cba10dc0-2ec1-41ba-b99e-1eb8fe51c61a' : CPart :> 'Wing'  { 
                                @CapellaID { eid = "cba10dc0-2ec1-41ba-b99e-1eb8fe51c61a"; sid = "cba10dc0-2ec1-41ba-b99e-1eb8fe51c61a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            port 'CP 4' : ComponentPort { 
                                @CapellaID { eid = "69fc2146-4b55-43cb-b2c7-22269e45b94a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '95e6d47d-3f50-4a6a-b826-647d31a35911' : PortAllocation
                                    allocate allocatedPort ::> 'Physical Functions'::'Root Physical Function'.'Support '.'FOP 3'
                                    to allocatingPort ::> 'CP 4'; 
                                ref :>> ownedPortAllocations =  ('95e6d47d-3f50-4a6a-b826-647d31a35911'); 
                                 
                            }  
                            port 'CP 5' : ComponentPort { 
                                @CapellaID { eid = "90c11696-6215-44f3-8f8e-9a20a293d087"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation 'a55be6ff-43c7-4b7f-80e6-fb179b3c015f' : PortAllocation
                                    allocate allocatedPort ::> 'Physical Functions'::'Root Physical Function'.'Support '.'FOP 2'
                                    to allocatingPort ::> 'CP 5'; 
                                ref allocation 'f29e8239-4e5e-4f75-99e6-82df563984a5' : PortAllocation
                                    allocate allocatedPort ::> 'Physical Functions'::'Root Physical Function'.'Duplicate 67'.'FOP 2'
                                    to allocatingPort ::> 'CP 5'; 
                                ref :>> ownedPortAllocations =  ('a55be6ff-43c7-4b7f-80e6-fb179b3c015f',
                                'f29e8239-4e5e-4f75-99e6-82df563984a5'); 
                                 
                            }  
                            part 'Fuselage' : PhysicalComponent { 
                                @CapellaID { eid = "986eb815-ed1b-45e4-a60f-0db3b665c245"; sid = "986eb815-ed1b-45e4-a60f-0db3b665c245"; } 
                                attribute :>> isAbstract = false; 
                                attribute :>> isActor = false; 
                                attribute :>> isHuman = false; 
                                attribute :>> kind = PhysicalComponentKind::UNSET; 
                                attribute :>> nature = PhysicalComponentNature::BEHAVIOR; 
                                 
                                 
                            }  
                            part 'Empennage' : PhysicalComponent { 
                                @CapellaID { eid = "8a776623-0546-4b5d-a961-1222c1b4f366"; sid = "8a776623-0546-4b5d-a961-1222c1b4f366"; } 
                                attribute :>> isAbstract = false; 
                                attribute :>> isActor = false; 
                                attribute :>> isHuman = false; 
                                attribute :>> kind = PhysicalComponentKind::UNSET; 
                                attribute :>> nature = PhysicalComponentNature::BEHAVIOR; 
                                 
                                 
                            }  
                            part 'Wing' : PhysicalComponent { 
                                @CapellaID { eid = "597b3df7-0890-4c95-97e0-41bbeb72d268"; sid = "597b3df7-0890-4c95-97e0-41bbeb72d268"; } 
                                attribute :>> isAbstract = false; 
                                attribute :>> isActor = false; 
                                attribute :>> isHuman = false; 
                                attribute :>> kind = PhysicalComponentKind::UNSET; 
                                attribute :>> nature = PhysicalComponentNature::BEHAVIOR; 
                                dependency 'b5a7fb03-5c5d-47e2-a84a-846c88cb4da3'
                                    from 'fc8c8686-5ee4-4222-ac35-7bd37b07c701'
                                    to  'Logical Architecture'::'Structure'::'UAV System'::'Drone'::'Airframe'::'Wing'::'bc7673df-9fe7-42d5-9190-832f6c967e09' { 
                                    @TransfoLink { 
                                        @CapellaID { eid = "b5a7fb03-5c5d-47e2-a84a-846c88cb4da3"; } 
                                    }  
                                }  
                                part 'fc8c8686-5ee4-4222-ac35-7bd37b07c701' : CPart :> 'Winglet'  { 
                                    @CapellaID { eid = "fc8c8686-5ee4-4222-ac35-7bd37b07c701"; sid = "fc8c8686-5ee4-4222-ac35-7bd37b07c701"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                     
                                }  
                                part 'Winglet' : PhysicalComponent { 
                                    @CapellaID { eid = "feed7369-ce68-416f-8497-02e7287961a2"; sid = "feed7369-ce68-416f-8497-02e7287961a2"; } 
                                    attribute :>> isAbstract = false; 
                                    attribute :>> isActor = false; 
                                    attribute :>> isHuman = false; 
                                    attribute :>> kind = PhysicalComponentKind::UNSET; 
                                    attribute :>> nature = PhysicalComponentNature::BEHAVIOR; 
                                     
                                     
                                }  
                                 
                                 
                                ref :>> ownedPhysicalComponents =  ('Winglet'); 
                            }  
                            ref :>> ownedFunctionalAllocation =  ('adc48c8e-a1b5-499a-ab4c-46476ca23274',
                            '43db8d91-a660-484b-bb3a-ff0e1a6c9a96',
                            '8c5de056-8b14-4c0e-852c-a890c8e797ec',
                            '0f0f6a7a-d683-464b-a6a8-f1df96245c83'); 
                             
                             
                            ref :>> ownedPhysicalComponents =  ('Fuselage',
                            'Empennage',
                            'Wing'); 
                        }  
                        part 'NLG Shock' : PhysicalComponent { 
                            @CapellaID { eid = "83e14e8d-eac5-4716-abe2-fd890ad2e2c0"; sid = "83e14e8d-eac5-4716-abe2-fd890ad2e2c0"; } 
                            attribute :>> isAbstract = false; 
                            attribute :>> isActor = false; 
                            attribute :>> isHuman = false; 
                            attribute :>> kind = PhysicalComponentKind::UNSET; 
                            attribute :>> nature = PhysicalComponentNature::BEHAVIOR; 
                            allocation '0ef57c98-eaa3-4103-9db5-db7ae03ca794' : ComponentFunctionalAllocation
                                allocate function ::> 'Physical Functions'::'Root Physical Function'.'Transmit NLG Forces'.'Dampen Spring'
                                to component ::> 'NLG Shock' { 
                                @CapellaID { eid = "0ef57c98-eaa3-4103-9db5-db7ae03ca794"; sid = "0ef57c98-eaa3-4103-9db5-db7ae03ca794"; } 
                                 
                            } 
                            perform 'Physical Functions'::'Root Physical Function'.'Transmit NLG Forces'.'Dampen Spring' ; 
                            port 'CP 1' : ComponentPort { 
                                @CapellaID { eid = "94c139e2-92b7-4a35-a292-f4dfdf8c8c29"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation '97455773-95e8-49ac-adc2-79135a5eed08' : PortAllocation
                                    allocate allocatedPort ::> 'Physical Functions'::'Root Physical Function'.'Transmit NLG Forces'.'Dampen Spring'.'FIP 1'
                                    to allocatingPort ::> 'CP 1'; 
                                ref :>> ownedPortAllocations =  ('97455773-95e8-49ac-adc2-79135a5eed08'); 
                                 
                            }  
                            port 'CP 2' : ComponentPort { 
                                @CapellaID { eid = "d49f8cc2-730a-4d61-8ea3-407853463990"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation 'f50db72e-5167-4d9f-94a4-2b1c611b18af' : PortAllocation
                                    allocate allocatedPort ::> 'Physical Functions'::'Root Physical Function'.'Transmit NLG Forces'.'Dampen Spring'.'FOP 1'
                                    to allocatingPort ::> 'CP 2'; 
                                ref :>> ownedPortAllocations =  ('f50db72e-5167-4d9f-94a4-2b1c611b18af'); 
                                 
                            }  
                            ref :>> ownedFunctionalAllocation =  ('0ef57c98-eaa3-4103-9db5-db7ae03ca794'); 
                             
                        }  
                        part 'NLG  Control Valve' : PhysicalComponent { 
                            @CapellaID { eid = "9062bd24-8511-43f7-a81e-2e1b995d9376"; sid = "9062bd24-8511-43f7-a81e-2e1b995d9376"; } 
                            attribute :>> isAbstract = false; 
                            attribute :>> isActor = false; 
                            attribute :>> isHuman = false; 
                            attribute :>> kind = PhysicalComponentKind::UNSET; 
                            attribute :>> nature = PhysicalComponentNature::BEHAVIOR; 
                            allocation '3100e03c-3518-4431-85ab-45bb1bf8ddae' : ComponentFunctionalAllocation
                                allocate function ::> 'Physical Functions'::'Root Physical Function'.'Measure'.'Actuate NLG'.'Control Pressure to Wheel'
                                to component ::> 'NLG  Control Valve' { 
                                @CapellaID { eid = "3100e03c-3518-4431-85ab-45bb1bf8ddae"; sid = "3100e03c-3518-4431-85ab-45bb1bf8ddae"; } 
                                 
                            } 
                            perform 'Physical Functions'::'Root Physical Function'.'Measure'.'Actuate NLG'.'Control Pressure to Wheel' ; 
                            port 'CP 1' : ComponentPort { 
                                @CapellaID { eid = "c0ad5dc3-bc0a-42a0-abe6-5427d0dfee44"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation '5462b3d1-4e31-4be9-8f1f-31693c323702' : PortAllocation
                                    allocate allocatedPort ::> 'Physical Functions'::'Root Physical Function'.'Measure'.'Actuate NLG'.'Control Pressure to Wheel'.'FIP 3'
                                    to allocatingPort ::> 'CP 1'; 
                                ref :>> ownedPortAllocations =  ('5462b3d1-4e31-4be9-8f1f-31693c323702'); 
                                 
                            }  
                            port 'CP 2' : ComponentPort { 
                                @CapellaID { eid = "ea947fbe-a871-4f4a-8b96-5952e8ef1ec9"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation 'a5a56364-8230-4bf3-b9f7-2e51c64058b2' : PortAllocation
                                    allocate allocatedPort ::> 'Physical Functions'::'Root Physical Function'.'Measure'.'Actuate NLG'.'Control Pressure to Wheel'.'FOP 1'
                                    to allocatingPort ::> 'CP 2'; 
                                ref :>> ownedPortAllocations =  ('a5a56364-8230-4bf3-b9f7-2e51c64058b2'); 
                                 
                            }  
                            port 'CP 3' : ComponentPort { 
                                @CapellaID { eid = "0b95219e-2e4d-4f9c-ad5d-8646d2ff71f3"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation '1e2c5141-b112-418e-9a9b-e484e0b137a6' : PortAllocation
                                    allocate allocatedPort ::> 'Physical Functions'::'Root Physical Function'.'Measure'.'Actuate NLG'.'Control Pressure to Wheel'.'FIP 1'
                                    to allocatingPort ::> 'CP 3'; 
                                ref :>> ownedPortAllocations =  ('1e2c5141-b112-418e-9a9b-e484e0b137a6'); 
                                 
                            }  
                            port 'CP 4' : ComponentPort { 
                                @CapellaID { eid = "df9d985f-6866-402a-97d0-bce662e4e71a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '12b47179-c492-405e-abb9-48687cd3b763' : PortAllocation
                                    allocate allocatedPort ::> 'Physical Functions'::'Root Physical Function'.'Measure'.'Actuate NLG'.'Control Pressure to Wheel'.'FOP 7'
                                    to allocatingPort ::> 'CP 4'; 
                                ref :>> ownedPortAllocations =  ('12b47179-c492-405e-abb9-48687cd3b763'); 
                                 
                            }  
                            ref :>> ownedFunctionalAllocation =  ('3100e03c-3518-4431-85ab-45bb1bf8ddae'); 
                             
                        }  
                        part 'NLG Uplock Sensor 2' : PhysicalComponent { 
                            @CapellaID { eid = "b00d3cb9-3c97-4158-88e8-87582ab23f49"; sid = "b00d3cb9-3c97-4158-88e8-87582ab23f49"; } 
                            attribute :>> isAbstract = false; 
                            attribute :>> isActor = false; 
                            attribute :>> isHuman = false; 
                            attribute :>> kind = PhysicalComponentKind::UNSET; 
                            attribute :>> nature = PhysicalComponentNature::BEHAVIOR; 
                            allocation '209fce39-445a-4446-81ab-d08cd9b39373' : ComponentFunctionalAllocation
                                allocate function ::> 'Physical Functions'::'Root Physical Function'.'Sense Hardware'.'Sense UPLock Position 2'
                                to component ::> 'NLG Uplock Sensor 2' { 
                                @CapellaID { eid = "209fce39-445a-4446-81ab-d08cd9b39373"; } 
                                 
                            } 
                            perform 'Physical Functions'::'Root Physical Function'.'Sense Hardware'.'Sense UPLock Position 2' ; 
                            port 'CP 1' : ComponentPort { 
                                @CapellaID { eid = "587f6dd7-04af-4a42-813f-19140ce7a500"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation 'bad3be12-54e0-4e06-877c-5264d0f2c2eb' : PortAllocation
                                    allocate allocatedPort ::> 'Physical Functions'::'Root Physical Function'.'Sense Hardware'.'Sense UPLock Position 2'.'FOP 5'
                                    to allocatingPort ::> 'CP 1'; 
                                ref :>> ownedPortAllocations =  ('bad3be12-54e0-4e06-877c-5264d0f2c2eb'); 
                                 
                            }  
                            ref :>> ownedFunctionalAllocation =  ('209fce39-445a-4446-81ab-d08cd9b39373'); 
                             
                        }  
                        part 'NLG Downlock Sensor 1' : PhysicalComponent { 
                            @CapellaID { eid = "2b4771b0-182d-4b91-a676-ea3c80843d2a"; sid = "2b4771b0-182d-4b91-a676-ea3c80843d2a"; } 
                            attribute :>> isAbstract = false; 
                            attribute :>> isActor = false; 
                            attribute :>> isHuman = false; 
                            attribute :>> kind = PhysicalComponentKind::UNSET; 
                            attribute :>> nature = PhysicalComponentNature::BEHAVIOR; 
                            allocation 'c0cf93d9-faed-4020-9318-f7ad252fde5b' : ComponentFunctionalAllocation
                                allocate function ::> 'Physical Functions'::'Root Physical Function'.'Sense Hardware'.'Sense DWNLock Position 1'
                                to component ::> 'NLG Downlock Sensor 1' { 
                                @CapellaID { eid = "c0cf93d9-faed-4020-9318-f7ad252fde5b"; } 
                                 
                            } 
                            perform 'Physical Functions'::'Root Physical Function'.'Sense Hardware'.'Sense DWNLock Position 1' ; 
                            port 'CP 1' : ComponentPort { 
                                @CapellaID { eid = "5f00e576-9987-4061-b79b-5948e0f5e769"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '3f55d7d7-b146-4e4a-ad18-5b8cd13749fe' : PortAllocation
                                    allocate allocatedPort ::> 'Physical Functions'::'Root Physical Function'.'Sense Hardware'.'Sense DWNLock Position 1'.'FOP 2'
                                    to allocatingPort ::> 'CP 1'; 
                                ref :>> ownedPortAllocations =  ('3f55d7d7-b146-4e4a-ad18-5b8cd13749fe'); 
                                 
                            }  
                            ref :>> ownedFunctionalAllocation =  ('c0cf93d9-faed-4020-9318-f7ad252fde5b'); 
                             
                        }  
                        part 'Weight on Wheelp Sensor 2' : PhysicalComponent { 
                            @CapellaID { eid = "3cc0b208-96d5-4c13-9f6e-6b9d4f5d5531"; sid = "3cc0b208-96d5-4c13-9f6e-6b9d4f5d5531"; } 
                            attribute :>> isAbstract = false; 
                            attribute :>> isActor = false; 
                            attribute :>> isHuman = false; 
                            attribute :>> kind = PhysicalComponentKind::UNSET; 
                            attribute :>> nature = PhysicalComponentNature::BEHAVIOR; 
                            allocation 'e5aa9fb4-a177-406f-a52b-b74506674366' : ComponentFunctionalAllocation
                                allocate function ::> 'Physical Functions'::'Root Physical Function'.'Sense Weight on Wheels 2'
                                to component ::> 'Weight on Wheelp Sensor 2' { 
                                @CapellaID { eid = "e5aa9fb4-a177-406f-a52b-b74506674366"; } 
                                 
                            } 
                            perform 'Physical Functions'::'Root Physical Function'.'Sense Weight on Wheels 2' ; 
                            port 'CP 1' : ComponentPort { 
                                @CapellaID { eid = "bfeef6ae-8bd0-4931-a0b0-e90dc0a80612"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '0ee8a3a8-e8da-4fc1-806a-7c17ffad5745' : PortAllocation
                                    allocate allocatedPort ::> 'Physical Functions'::'Root Physical Function'.'Sense Weight on Wheels 2'.'FOP 1'
                                    to allocatingPort ::> 'CP 1'; 
                                ref :>> ownedPortAllocations =  ('0ee8a3a8-e8da-4fc1-806a-7c17ffad5745'); 
                                 
                            }  
                            ref :>> ownedFunctionalAllocation =  ('e5aa9fb4-a177-406f-a52b-b74506674366'); 
                             
                        }  
                        part 'NLG Wheel' : PhysicalComponent { 
                            @CapellaID { eid = "d37db216-7e38-4f34-ad4e-c1070c924e79"; sid = "d37db216-7e38-4f34-ad4e-c1070c924e79"; } 
                            attribute :>> isAbstract = false; 
                            attribute :>> isActor = false; 
                            attribute :>> isHuman = false; 
                            attribute :>> kind = PhysicalComponentKind::UNSET; 
                            attribute :>> nature = PhysicalComponentNature::BEHAVIOR; 
                            allocation '8241d1f4-dbb9-46a9-89f0-a783ff9ddf47' : ComponentFunctionalAllocation
                                allocate function ::> 'Physical Functions'::'Root Physical Function'.'Measure'.'Actuate NLG'.'Apply Force Runway'
                                to component ::> 'NLG Wheel' { 
                                @CapellaID { eid = "8241d1f4-dbb9-46a9-89f0-a783ff9ddf47"; sid = "8241d1f4-dbb9-46a9-89f0-a783ff9ddf47"; } 
                                 
                            } 
                            perform 'Physical Functions'::'Root Physical Function'.'Measure'.'Actuate NLG'.'Apply Force Runway' ; 
                            allocation 'fd4e508d-28af-4a1b-a521-1507f85327cd' : ComponentFunctionalAllocation
                                allocate function ::> 'Physical Functions'::'Root Physical Function'.'Slow Rotation'
                                to component ::> 'NLG Wheel' { 
                                @CapellaID { eid = "fd4e508d-28af-4a1b-a521-1507f85327cd"; sid = "fd4e508d-28af-4a1b-a521-1507f85327cd"; } 
                                 
                            } 
                            perform 'Physical Functions'::'Root Physical Function'.'Slow Rotation' ; 
                            allocation '97c6ce13-5403-4936-b458-bef5533554fe' : ComponentFunctionalAllocation
                                allocate function ::> 'Physical Functions'::'Root Physical Function'.'Provide Spring Support'
                                to component ::> 'NLG Wheel' { 
                                @CapellaID { eid = "97c6ce13-5403-4936-b458-bef5533554fe"; } 
                                 
                            } 
                            perform 'Physical Functions'::'Root Physical Function'.'Provide Spring Support' ; 
                            port 'CP 1' : ComponentPort { 
                                @CapellaID { eid = "459eaa80-4671-406c-92a1-e32c0a6afb03"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation 'ec5f4f3b-4e15-4984-b28e-8ddcfb40e133' : PortAllocation
                                    allocate allocatedPort ::> 'Physical Functions'::'Root Physical Function'.'Measure'.'Actuate NLG'.'Apply Force Runway'.'FIP 1'
                                    to allocatingPort ::> 'CP 1'; 
                                ref :>> ownedPortAllocations =  ('ec5f4f3b-4e15-4984-b28e-8ddcfb40e133'); 
                                 
                            }  
                            port 'CP 2' : ComponentPort { 
                                @CapellaID { eid = "4778e1d3-fb37-4a9d-8d4a-ee55c8af7d36"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '0bcd1b39-77a6-44e0-b2ed-fc8c6b12ad2f' : PortAllocation
                                    allocate allocatedPort ::> 'Physical Functions'::'Root Physical Function'.'Measure'.'Actuate NLG'.'Apply Force Runway'.'FOP 3'
                                    to allocatingPort ::> 'CP 2'; 
                                ref :>> ownedPortAllocations =  ('0bcd1b39-77a6-44e0-b2ed-fc8c6b12ad2f'); 
                                 
                            }  
                            port 'CP 3' : ComponentPort { 
                                @CapellaID { eid = "abc85de3-5f87-4e26-99d1-deb90cd54b4a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation '3fdbc2c7-6b1b-4df4-bcef-4a55657b160c' : PortAllocation
                                    allocate allocatedPort ::> 'Physical Functions'::'Root Physical Function'.'Provide Spring Support'.'FIP 1'
                                    to allocatingPort ::> 'CP 3'; 
                                ref :>> ownedPortAllocations =  ('3fdbc2c7-6b1b-4df4-bcef-4a55657b160c'); 
                                 
                            }  
                            port 'CP 4' : ComponentPort { 
                                @CapellaID { eid = "381777bb-8582-4ad2-b323-8fa0d44bccbe"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '92065d93-4f1e-41f6-9a75-14538dff2b45' : PortAllocation
                                    allocate allocatedPort ::> 'Physical Functions'::'Root Physical Function'.'Measure'.'Actuate NLG'.'Apply Force Runway'.'FOP 1'
                                    to allocatingPort ::> 'CP 4'; 
                                ref allocation '2a9a2049-6d8b-4a01-bb25-dbd42cb7e378' : PortAllocation
                                    allocate allocatedPort ::> 'Physical Functions'::'Root Physical Function'.'Slow Rotation'.'FOP 1'
                                    to allocatingPort ::> 'CP 4'; 
                                ref :>> ownedPortAllocations =  ('92065d93-4f1e-41f6-9a75-14538dff2b45',
                                '2a9a2049-6d8b-4a01-bb25-dbd42cb7e378'); 
                                 
                            }  
                            ref :>> ownedFunctionalAllocation =  ('8241d1f4-dbb9-46a9-89f0-a783ff9ddf47',
                            'fd4e508d-28af-4a1b-a521-1507f85327cd',
                            '97c6ce13-5403-4936-b458-bef5533554fe'); 
                             
                        }  
                        part 'NLG Doors Selector Valve' : PhysicalComponent { 
                            doc /*
                            Realizes the Control Pressure function: takes hydraulic supply and an NLG Door command as inputs, and outputs regulated pressure to the door actuator (via H-MLG Door DV) and the dump valve (via Dump Valve to Selector Valve Pressure).
                            */ 
                            @CapellaID { eid = "cd9036d8-23db-48f9-825b-3861748237a5"; sid = "cd9036d8-23db-48f9-825b-3861748237a5"; } 
                            attribute :>> isAbstract = false; 
                            attribute :>> isActor = false; 
                            attribute :>> isHuman = false; 
                            attribute :>> kind = PhysicalComponentKind::UNSET; 
                            attribute :>> nature = PhysicalComponentNature::BEHAVIOR; 
                            allocation '25c8b07f-8730-4ad2-ba21-263a9223933f' : ComponentFunctionalAllocation
                                allocate function ::> 'Physical Functions'::'Root Physical Function'.'Control Pressure'
                                to component ::> 'NLG Doors Selector Valve' { 
                                @CapellaID { eid = "25c8b07f-8730-4ad2-ba21-263a9223933f"; } 
                                 
                            } 
                            perform 'Physical Functions'::'Root Physical Function'.'Control Pressure' ; 
                            port 'CP 2' : ComponentPort { 
                                @CapellaID { eid = "3f2b1377-e219-4a6f-97d9-e25575efd0ac"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '0f6bcf82-b60c-4cfb-a982-038ebedf724d' : PortAllocation
                                    allocate allocatedPort ::> 'Physical Functions'::'Root Physical Function'.'Control Pressure'.'FOP 2'
                                    to allocatingPort ::> 'CP 2'; 
                                ref :>> ownedPortAllocations =  ('0f6bcf82-b60c-4cfb-a982-038ebedf724d'); 
                                 
                            }  
                            port 'CP 3' : ComponentPort { 
                                @CapellaID { eid = "e655f23a-af6f-4def-9ef3-fcbb0e6c8a61"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation '9291b934-cc77-4868-bf35-1267f4ffb58d' : PortAllocation
                                    allocate allocatedPort ::> 'Physical Functions'::'Root Physical Function'.'Control Pressure'.'FOP 1'
                                    to allocatingPort ::> 'CP 3'; 
                                ref :>> ownedPortAllocations =  ('9291b934-cc77-4868-bf35-1267f4ffb58d'); 
                                 
                            }  
                            port 'CP 4' : ComponentPort { 
                                @CapellaID { eid = "065ec579-a849-4726-905f-98a7a66676e7"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation 'ff5ed22d-2725-4a59-b0b7-65a271867613' : PortAllocation
                                    allocate allocatedPort ::> 'Physical Functions'::'Root Physical Function'.'Control Pressure'.'FIP 1'
                                    to allocatingPort ::> 'CP 4'; 
                                ref :>> ownedPortAllocations =  ('ff5ed22d-2725-4a59-b0b7-65a271867613'); 
                                 
                            }  
                            ref :>> ownedFunctionalAllocation =  ('25c8b07f-8730-4ad2-ba21-263a9223933f'); 
                             
                        }  
                        part 'Isolation Valve' : PhysicalComponent { 
                            @CapellaID { eid = "b061fc0a-491a-4b1d-9526-1448f3f292f8"; } 
                            attribute :>> isAbstract = false; 
                            attribute :>> isActor = false; 
                            attribute :>> isHuman = false; 
                            attribute :>> kind = PhysicalComponentKind::UNSET; 
                            attribute :>> nature = PhysicalComponentNature::BEHAVIOR; 
                            allocation '170cda34-5319-45c1-89b1-f1fa49c92e34' : ComponentFunctionalAllocation
                                allocate function ::> 'Physical Functions'::'Root Physical Function'.'Isolate '
                                to component ::> 'Isolation Valve' { 
                                @CapellaID { eid = "170cda34-5319-45c1-89b1-f1fa49c92e34"; } 
                                 
                            } 
                            perform 'Physical Functions'::'Root Physical Function'.'Isolate ' ; 
                            port 'CP 1' : ComponentPort { 
                                @CapellaID { eid = "85480812-185b-4b18-b5ed-46d6e9b0bed9"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation '2c75c396-fdad-463c-b8f9-8d2d9e90defb' : PortAllocation
                                    allocate allocatedPort ::> 'Physical Functions'::'Root Physical Function'.'Isolate '.'FIP 1'
                                    to allocatingPort ::> 'CP 1'; 
                                ref :>> ownedPortAllocations =  ('2c75c396-fdad-463c-b8f9-8d2d9e90defb'); 
                                 
                            }  
                            port 'CP 2' : ComponentPort { 
                                @CapellaID { eid = "5d575494-13e6-425c-a27e-5535bf953ca3"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '9e33ad14-fde3-42a9-bd1e-8ddddc7baea2' : PortAllocation
                                    allocate allocatedPort ::> 'Physical Functions'::'Root Physical Function'.'Isolate '.'FOP 1'
                                    to allocatingPort ::> 'CP 2'; 
                                ref :>> ownedPortAllocations =  ('9e33ad14-fde3-42a9-bd1e-8ddddc7baea2'); 
                                 
                            }  
                            ref :>> ownedFunctionalAllocation =  ('170cda34-5319-45c1-89b1-f1fa49c92e34'); 
                             
                        }  
                        part 'Blue Hydraulic Pump' : PhysicalComponent { 
                            @CapellaID { eid = "0e1a1eee-c0ba-49db-a16f-a1f4d92c49ee"; } 
                            attribute :>> isAbstract = false; 
                            attribute :>> isActor = false; 
                            attribute :>> isHuman = false; 
                            attribute :>> kind = PhysicalComponentKind::UNSET; 
                            attribute :>> nature = PhysicalComponentNature::BEHAVIOR; 
                            allocation 'b905a32f-fac6-4c4c-8388-43aa526c5fc5' : ComponentFunctionalAllocation
                                allocate function ::> 'Physical Functions'::'Root Physical Function'.'Pump Fluid'
                                to component ::> 'Blue Hydraulic Pump' { 
                                @CapellaID { eid = "b905a32f-fac6-4c4c-8388-43aa526c5fc5"; } 
                                 
                            } 
                            perform 'Physical Functions'::'Root Physical Function'.'Pump Fluid' ; 
                            port 'CP 1' : ComponentPort { 
                                @CapellaID { eid = "052421be-7481-4d3d-b204-87700e6345fe"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation '7ceedc4b-8981-47d9-97c2-e796ae9608b1' : PortAllocation
                                    allocate allocatedPort ::> 'Physical Functions'::'Root Physical Function'.'Pump Fluid'.'Fluid'
                                    to allocatingPort ::> 'CP 1'; 
                                ref :>> ownedPortAllocations =  ('7ceedc4b-8981-47d9-97c2-e796ae9608b1'); 
                                 
                            }  
                            port 'CP 2' : ComponentPort { 
                                @CapellaID { eid = "8060289d-9981-4cf6-b818-ecd33eb38b59"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '93338132-6e6a-44d2-96d3-98a68219352b' : PortAllocation
                                    allocate allocatedPort ::> 'Physical Functions'::'Root Physical Function'.'Pump Fluid'.'FOP 1'
                                    to allocatingPort ::> 'CP 2'; 
                                ref :>> ownedPortAllocations =  ('93338132-6e6a-44d2-96d3-98a68219352b'); 
                                 
                            }  
                            ref :>> ownedFunctionalAllocation =  ('b905a32f-fac6-4c4c-8388-43aa526c5fc5'); 
                             
                        }  
                        part 'Shutoff Valve' : PhysicalComponent { 
                            @CapellaID { eid = "e7dd014a-678f-446e-9985-658c6bba7b6d"; } 
                            attribute :>> isAbstract = false; 
                            attribute :>> isActor = false; 
                            attribute :>> isHuman = false; 
                            attribute :>> kind = PhysicalComponentKind::UNSET; 
                            attribute :>> nature = PhysicalComponentNature::BEHAVIOR; 
                            allocation 'e8b846be-6c1d-4515-984f-28457ae05669' : ComponentFunctionalAllocation
                                allocate function ::> 'Physical Functions'::'Root Physical Function'.'Regulate'
                                to component ::> 'Shutoff Valve' { 
                                @CapellaID { eid = "e8b846be-6c1d-4515-984f-28457ae05669"; } 
                                 
                            } 
                            perform 'Physical Functions'::'Root Physical Function'.'Regulate' ; 
                            port 'CP 1' : ComponentPort { 
                                @CapellaID { eid = "c199b609-d261-4f0a-ad89-7b666da3dc3f"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                 
                            }  
                            port 'CP 2' : ComponentPort { 
                                @CapellaID { eid = "8e1d751f-a393-4953-9dee-cd67555a6407"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation 'fb6ab369-cafd-40f9-bac0-8b6edf2f8716' : PortAllocation
                                    allocate allocatedPort ::> 'Physical Functions'::'Root Physical Function'.'Regulate'.'FOP 1'
                                    to allocatingPort ::> 'CP 2'; 
                                ref :>> ownedPortAllocations =  ('fb6ab369-cafd-40f9-bac0-8b6edf2f8716'); 
                                 
                            }  
                            ref :>> ownedFunctionalAllocation =  ('e8b846be-6c1d-4515-984f-28457ae05669'); 
                             
                        }  
                        part 'Extension Retraction Lever' : PhysicalComponent { 
                            @CapellaID { eid = "85ed6e68-b5f7-4b2d-9217-d057d2b0fe4e"; sid = "85ed6e68-b5f7-4b2d-9217-d057d2b0fe4e"; } 
                            attribute :>> isAbstract = false; 
                            attribute :>> isActor = false; 
                            attribute :>> isHuman = false; 
                            attribute :>> kind = PhysicalComponentKind::UNSET; 
                            attribute :>> nature = PhysicalComponentNature::BEHAVIOR; 
                            allocation '97d0fe32-800b-4212-b055-1effb05d74b9' : ComponentFunctionalAllocation
                                allocate function ::> 'Physical Functions'::'Root Physical Function'.'Provide Landing Gear Control'.'Provide'
                                to component ::> 'Extension Retraction Lever' { 
                                @CapellaID { eid = "97d0fe32-800b-4212-b055-1effb05d74b9"; sid = "97d0fe32-800b-4212-b055-1effb05d74b9"; } 
                                 
                            } 
                            perform 'Physical Functions'::'Root Physical Function'.'Provide Landing Gear Control'.'Provide' ; 
                            port 'CP 1' : ComponentPort { 
                                @CapellaID { eid = "6cb8e779-d6f9-46d3-9c17-9a63f2348283"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation '1a48528b-97ea-4ff6-9a8a-d89affbd0556' : PortAllocation
                                    allocate allocatedPort ::> 'Physical Functions'::'Root Physical Function'.'Provide Landing Gear Control'.'Provide'.'FIP 3'
                                    to allocatingPort ::> 'CP 1'; 
                                ref :>> ownedPortAllocations =  ('1a48528b-97ea-4ff6-9a8a-d89affbd0556'); 
                                 
                            }  
                            port 'CP 2' : ComponentPort { 
                                @CapellaID { eid = "fc2842fa-8e67-4e73-ae8b-de37ba76ede9"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '7f732ee5-b871-4e36-af93-a7578eb74d3d' : PortAllocation
                                    allocate allocatedPort ::> 'Physical Functions'::'Root Physical Function'.'Provide Landing Gear Control'.'Provide'.'FOP 1'
                                    to allocatingPort ::> 'CP 2'; 
                                ref :>> ownedPortAllocations =  ('7f732ee5-b871-4e36-af93-a7578eb74d3d'); 
                                 
                            }  
                            ref :>> ownedFunctionalAllocation =  ('97d0fe32-800b-4212-b055-1effb05d74b9'); 
                             
                             
                        }  
                        part 'PC 40' : PhysicalComponent { 
                            @CapellaID { eid = "e079338d-aacc-4cec-8d76-9544bd86bca1"; } 
                            attribute :>> isAbstract = false; 
                            attribute :>> isActor = false; 
                            attribute :>> isHuman = false; 
                            attribute :>> kind = PhysicalComponentKind::UNSET; 
                            attribute :>> nature = PhysicalComponentNature::BEHAVIOR; 
                            allocation 'fc4356d3-94f9-4cf9-a0d6-c9e795db213b' : ComponentFunctionalAllocation
                                allocate function ::> 'Physical Functions'::'Root Physical Function'.'PhysicalFunction 41'
                                to component ::> 'PC 40' { 
                                @CapellaID { eid = "fc4356d3-94f9-4cf9-a0d6-c9e795db213b"; } 
                                 
                            } 
                            perform 'Physical Functions'::'Root Physical Function'.'PhysicalFunction 41' ; 
                            ref :>> ownedFunctionalAllocation =  ('fc4356d3-94f9-4cf9-a0d6-c9e795db213b'); 
                             
                        }  
                        part 'NLG' : PhysicalComponent { 
                            @CapellaID { eid = "a1145125-400c-4b8f-8cd8-fa72b328cdbf"; sid = "a1145125-400c-4b8f-8cd8-fa72b328cdbf"; } 
                            attribute :>> isAbstract = false; 
                            attribute :>> isActor = false; 
                            attribute :>> isHuman = false; 
                            attribute :>> kind = PhysicalComponentKind::UNSET; 
                            attribute :>> nature = PhysicalComponentNature::BEHAVIOR; 
                             
                             
                        }  
                        part 'H3' : PhysicalComponent { 
                            @CapellaID { eid = "d03197ec-6176-4903-b930-b0b45de412bd"; sid = "d03197ec-6176-4903-b930-b0b45de412bd"; } 
                            attribute :>> isAbstract = false; 
                            attribute :>> isActor = false; 
                            attribute :>> isHuman = false; 
                            attribute :>> kind = PhysicalComponentKind::UNSET; 
                            attribute :>> nature = PhysicalComponentNature::BEHAVIOR; 
                            allocation '7779b3f1-cab0-436a-8a37-5d721d9aea68' : ComponentFunctionalAllocation
                                allocate function ::> 'Physical Functions'::'Root Physical Function'.'Supply H3 Pressure'
                                to component ::> 'H3' { 
                                @CapellaID { eid = "7779b3f1-cab0-436a-8a37-5d721d9aea68"; sid = "7779b3f1-cab0-436a-8a37-5d721d9aea68"; } 
                                 
                            } 
                            perform 'Physical Functions'::'Root Physical Function'.'Supply H3 Pressure' ; 
                            port 'CP 1' : ComponentPort { 
                                @CapellaID { eid = "7a4dc58f-2b90-4dfb-bac0-51786a303937"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '2571a611-72cd-4d21-ae26-f735a1895c57' : PortAllocation
                                    allocate allocatedPort ::> 'Physical Functions'::'Root Physical Function'.'Supply H3 Pressure'.'FOP 2'
                                    to allocatingPort ::> 'CP 1'; 
                                ref :>> ownedPortAllocations =  ('2571a611-72cd-4d21-ae26-f735a1895c57'); 
                                 
                            }  
                            port 'CP 2' : ComponentPort { 
                                @CapellaID { eid = "31787eed-9108-42c7-a90c-2ca0fb604f00"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '535a953a-5735-47f6-a886-3914df4f0161' : PortAllocation
                                    allocate allocatedPort ::> 'Physical Functions'::'Root Physical Function'.'Supply H3 Pressure'.'FOP 1'
                                    to allocatingPort ::> 'CP 2'; 
                                ref :>> ownedPortAllocations =  ('535a953a-5735-47f6-a886-3914df4f0161'); 
                                 
                            }  
                            port 'CP 3' : ComponentPort { 
                                @CapellaID { eid = "f0ced1e4-72b5-4dfe-92a9-f9e7a4d669d3"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation 'd048a711-ba3e-455a-b888-b5fc208cea1a' : PortAllocation
                                    allocate allocatedPort ::> 'Physical Functions'::'Root Physical Function'.'Supply H3 Pressure'.'FIP 2'
                                    to allocatingPort ::> 'CP 3'; 
                                ref :>> ownedPortAllocations =  ('d048a711-ba3e-455a-b888-b5fc208cea1a'); 
                                 
                            }  
                            ref :>> ownedFunctionalAllocation =  ('7779b3f1-cab0-436a-8a37-5d721d9aea68'); 
                             
                             
                        }  
                        part 'Fuel and Power System' : PhysicalComponent { 
                            @CapellaID { eid = "fae8bf1f-2bb9-4a2c-9668-c1df0a6d1745"; } 
                            attribute :>> isAbstract = false; 
                            attribute :>> isActor = false; 
                            attribute :>> isHuman = false; 
                            attribute :>> kind = PhysicalComponentKind::UNSET; 
                            attribute :>> nature = PhysicalComponentNature::BEHAVIOR; 
                            allocation 'a657f31a-0620-43d7-8b73-9c09e1d7b90b' : ComponentFunctionalAllocation
                                allocate function ::> 'Physical Functions'::'Root Physical Function'.'Provide'
                                to component ::> 'Fuel and Power System' { 
                                @CapellaID { eid = "a657f31a-0620-43d7-8b73-9c09e1d7b90b"; } 
                                 
                            } 
                            perform 'Physical Functions'::'Root Physical Function'.'Provide' ; 
                            interface '3d2d91ab-6561-4b93-ac31-4cb688f46b8a' : ComponentExchange 
                                connect source ::> 'H R'.'CP 2'
                                to  target ::> 'H2'.'CP 1' { 
                                @CapellaID { eid = "3d2d91ab-6561-4b93-ac31-4cb688f46b8a"; } 
                                attribute :>> kind = ComponentExchangeKind::FLOW; 
                                attribute :>> interfaceName = "H Reservoir to H2"; 
                                attribute :>> isOriented = false; 
                                allocation '8a21267e-5b48-48d1-af69-b3117a635973' : ComponentExchangeFunctionalExchangeAllocation
                                    allocate functionalExchange ::> 'Physical Functions'::'Root Physical Function'.'6e4c5e21-12e9-4feb-814e-b7c8aa43f8ea'
                                    to componentExchange ::> '3d2d91ab-6561-4b93-ac31-4cb688f46b8a' { 
                                    @CapellaID { eid = "8a21267e-5b48-48d1-af69-b3117a635973"; } 
                                     
                                }  
                                 
                                ref :>> ownedComponentExchangeFunctionalExchangeAllocations =  ('8a21267e-5b48-48d1-af69-b3117a635973'); 
                            }  
                            part '2d01be52-4237-4b3f-b61c-4443ad4cb71d' : CPart :> 'ORS '  { 
                                @CapellaID { eid = "2d01be52-4237-4b3f-b61c-4443ad4cb71d"; sid = "2d01be52-4237-4b3f-b61c-4443ad4cb71d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part '51742133-7795-453d-86db-1ac786344f3a' : CPart :> 'H R'  { 
                                @CapellaID { eid = "51742133-7795-453d-86db-1ac786344f3a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part '5e39a677-77d9-4af8-a2b3-26824e320f34' : CPart :> 'Junction'  { 
                                @CapellaID { eid = "5e39a677-77d9-4af8-a2b3-26824e320f34"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part 'ad74f09b-9131-4a78-ab84-ad42de46af1c' : CPart :> 'Selector Valve'  { 
                                @CapellaID { eid = "ad74f09b-9131-4a78-ab84-ad42de46af1c"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part '7143335a-c190-4f06-9e8c-2de9547fea40' : CPart :> 'Audio'  { 
                                @CapellaID { eid = "7143335a-c190-4f06-9e8c-2de9547fea40"; sid = "7143335a-c190-4f06-9e8c-2de9547fea40"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part 'c0203ad1-a911-42f8-bd95-83b39df5bfac' : CPart :> 'MC Comp'  { 
                                @CapellaID { eid = "c0203ad1-a911-42f8-bd95-83b39df5bfac"; sid = "c0203ad1-a911-42f8-bd95-83b39df5bfac"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part '37e28ec9-9e30-4740-978f-68fdcd7461d0' : CPart :> 'NLG Door'  { 
                                @CapellaID { eid = "37e28ec9-9e30-4740-978f-68fdcd7461d0"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part '43702048-23d3-441a-adfe-e2872730f75b' : CPart :> 'Firm'  { 
                                @CapellaID { eid = "43702048-23d3-441a-adfe-e2872730f75b"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part 'b4eca515-0a19-4c0e-968b-1a7ffd9ae240' : CPart :> 'Dump Control'  { 
                                @CapellaID { eid = "b4eca515-0a19-4c0e-968b-1a7ffd9ae240"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part '00ce9c69-5878-4780-bc4e-868d34e6e706' : CPart :> 'Accumulator'  { 
                                @CapellaID { eid = "00ce9c69-5878-4780-bc4e-868d34e6e706"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part '0bfea9de-7cea-42ed-9ad2-d930ca24d9d4' : CPart :> 'FLIR'  { 
                                @CapellaID { eid = "0bfea9de-7cea-42ed-9ad2-d930ca24d9d4"; sid = "0bfea9de-7cea-42ed-9ad2-d930ca24d9d4"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part 'a1468a51-64d3-45ed-b71f-2a6b00c95928' : CPart :> 'SW'  { 
                                @CapellaID { eid = "a1468a51-64d3-45ed-b71f-2a6b00c95928"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part 'cf6df715-4cd6-41a8-9a24-c293c242811f' : CPart :> 'Hydrualic Controls'  { 
                                @CapellaID { eid = "cf6df715-4cd6-41a8-9a24-c293c242811f"; sid = "cf6df715-4cd6-41a8-9a24-c293c242811f"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part 'aae4ae38-86c3-4743-b346-0301611e1823' : CPart :> 'Green Hydaulic Pump'  { 
                                @CapellaID { eid = "aae4ae38-86c3-4743-b346-0301611e1823"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part 'c7478463-a226-4394-98f2-4189b801342c' : CPart :> 'H2'  { 
                                @CapellaID { eid = "c7478463-a226-4394-98f2-4189b801342c"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                 
                            }  
                            part 'ORS ' : PhysicalComponent { 
                                @CapellaID { eid = "c0047cee-2a57-43c2-a7b2-4bf96f376ada"; sid = "c0047cee-2a57-43c2-a7b2-4bf96f376ada"; } 
                                attribute :>> isAbstract = false; 
                                attribute :>> isActor = false; 
                                attribute :>> isHuman = false; 
                                attribute :>> kind = PhysicalComponentKind::UNSET; 
                                attribute :>> nature = PhysicalComponentNature::BEHAVIOR; 
                                allocation '69b942c7-e518-48ad-a4bb-52dc117af5a0' : ComponentFunctionalAllocation
                                    allocate function ::> 'Physical Functions'::'Root Physical Function'.'Locate Trapped People'
                                    to component ::> 'ORS ' { 
                                    @CapellaID { eid = "69b942c7-e518-48ad-a4bb-52dc117af5a0"; sid = "69b942c7-e518-48ad-a4bb-52dc117af5a0"; } 
                                     
                                } 
                                perform 'Physical Functions'::'Root Physical Function'.'Locate Trapped People' ; 
                                allocation 'cae3d662-4c55-4076-87ef-ea46ed2fb5d3' : ComponentFunctionalAllocation
                                    allocate function ::> 'Physical Functions'::'Root Physical Function'.'Image Storage'
                                    to component ::> 'ORS ' { 
                                    @CapellaID { eid = "cae3d662-4c55-4076-87ef-ea46ed2fb5d3"; sid = "cae3d662-4c55-4076-87ef-ea46ed2fb5d3"; } 
                                     
                                } 
                                perform 'Physical Functions'::'Root Physical Function'.'Image Storage' ; 
                                allocation 'c97128de-841e-4978-aa85-be6f4448a598' : ComponentFunctionalAllocation
                                    allocate function ::> 'Physical Functions'::'Root Physical Function'.'Activate Scan'
                                    to component ::> 'ORS ' { 
                                    @CapellaID { eid = "c97128de-841e-4978-aa85-be6f4448a598"; sid = "c97128de-841e-4978-aa85-be6f4448a598"; } 
                                     
                                } 
                                perform 'Physical Functions'::'Root Physical Function'.'Activate Scan' ; 
                                port 'CP 1' : ComponentPort { 
                                    @CapellaID { eid = "c1c61629-5723-46fb-ba74-67b714703d0d"; sid = "c1c61629-5723-46fb-ba74-67b714703d0d"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation 'c44214e6-809d-4541-9abb-a17a7ed206a2' : PortAllocation
                                        allocate allocatedPort ::> 'Physical Functions'::'Root Physical Function'.'Image Storage'.'inVideo'
                                        to allocatingPort ::> 'CP 1'; 
                                    ref allocation 'ebef0c8d-e87f-4beb-a3f7-411e2a8c6aa2' : PortAllocation
                                        allocate allocatedPort ::> 'Physical Functions'::'Root Physical Function'.'Image Storage'.'inPhotos'
                                        to allocatingPort ::> 'CP 1'; 
                                    ref allocation '884039a0-7971-4e4f-af1f-64a5c675559c' : PortAllocation
                                        allocate allocatedPort ::> 'Physical Functions'::'Root Physical Function'.'Activate Scan'.'FOP 1'
                                        to allocatingPort ::> 'CP 1'; 
                                    ref allocation 'f7454c6e-edde-4559-abc2-eb2f8bec82e1' : PortAllocation
                                        allocate allocatedPort ::> 'Physical Functions'::'Root Physical Function'.'Activate Scan'.'FOP 2'
                                        to allocatingPort ::> 'CP 1'; 
                                    ref :>> ownedPortAllocations =  ('c44214e6-809d-4541-9abb-a17a7ed206a2',
                                    'ebef0c8d-e87f-4beb-a3f7-411e2a8c6aa2',
                                    '884039a0-7971-4e4f-af1f-64a5c675559c',
                                    'f7454c6e-edde-4559-abc2-eb2f8bec82e1'); 
                                     
                                }  
                                port 'CP 2' : ComponentPort { 
                                    @CapellaID { eid = "4b547e75-61ce-4cab-875c-556fab8e30c1"; sid = "4b547e75-61ce-4cab-875c-556fab8e30c1"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::OUT; 
                                    attribute :>> isUnique = false; 
                                    ref allocation '7d4ee2e7-bbfd-48f9-b7e0-535c433e20ea' : PortAllocation
                                        allocate allocatedPort ::> 'Physical Functions'::'Root Physical Function'.'Locate Trapped People'.'outLocation'
                                        to allocatingPort ::> 'CP 2'; 
                                    ref allocation '2db37b30-2de8-4d7d-9d88-5c74b024b6c2' : PortAllocation
                                        allocate allocatedPort ::> 'Physical Functions'::'Root Physical Function'.'Locate Trapped People'.'FOP 2'
                                        to allocatingPort ::> 'CP 2'; 
                                    ref allocation '90b4a5eb-ac03-4350-926f-b11530e0306c' : PortAllocation
                                        allocate allocatedPort ::> 'Physical Functions'::'Root Physical Function'.'Image Storage'.'FOP 2'
                                        to allocatingPort ::> 'CP 2'; 
                                    ref :>> ownedPortAllocations =  ('7d4ee2e7-bbfd-48f9-b7e0-535c433e20ea',
                                    '2db37b30-2de8-4d7d-9d88-5c74b024b6c2',
                                    '90b4a5eb-ac03-4350-926f-b11530e0306c'); 
                                     
                                }  
                                port 'CP 3' : ComponentPort { 
                                    @CapellaID { eid = "b9dda931-d487-4038-8a77-f0e6365caffc"; sid = "b9dda931-d487-4038-8a77-f0e6365caffc"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '4265d9d6-b10c-484b-bc46-b2183d592009' : PortAllocation
                                        allocate allocatedPort ::> 'Physical Functions'::'Root Physical Function'.'Activate Scan'.'FIP 2'
                                        to allocatingPort ::> 'CP 3'; 
                                    ref :>> ownedPortAllocations =  ('4265d9d6-b10c-484b-bc46-b2183d592009'); 
                                     
                                }  
                                ref :>> ownedFunctionalAllocation =  ('69b942c7-e518-48ad-a4bb-52dc117af5a0',
                                'cae3d662-4c55-4076-87ef-ea46ed2fb5d3',
                                'c97128de-841e-4978-aa85-be6f4448a598'); 
                                 
                            }  
                            part 'H R' : PhysicalComponent { 
                                @CapellaID { eid = "ec03fe30-3864-4f79-9365-c09062e1e88e"; } 
                                attribute :>> isAbstract = false; 
                                attribute :>> isActor = false; 
                                attribute :>> isHuman = false; 
                                attribute :>> kind = PhysicalComponentKind::UNSET; 
                                attribute :>> nature = PhysicalComponentNature::BEHAVIOR; 
                                allocation '6b61e820-3f4d-423e-9ebb-515503a34561' : ComponentFunctionalAllocation
                                    allocate function ::> 'Physical Functions'::'Root Physical Function'.'Store H Fluid'
                                    to component ::> 'H R' { 
                                    @CapellaID { eid = "6b61e820-3f4d-423e-9ebb-515503a34561"; } 
                                     
                                } 
                                perform 'Physical Functions'::'Root Physical Function'.'Store H Fluid' ; 
                                port 'CP 1' : ComponentPort { 
                                    @CapellaID { eid = "153d634c-8bea-494d-8893-ad697362cbe3"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation 'e65f4b36-8660-4890-9afa-69ec63fe2401' : PortAllocation
                                        allocate allocatedPort ::> 'Physical Functions'::'Root Physical Function'.'Store H Fluid'.'FIP 2'
                                        to allocatingPort ::> 'CP 1'; 
                                    ref :>> ownedPortAllocations =  ('e65f4b36-8660-4890-9afa-69ec63fe2401'); 
                                     
                                }  
                                port 'CP 2' : ComponentPort { 
                                    @CapellaID { eid = "62755e62-0d9a-4a24-80a9-45043b3604bd"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::OUT; 
                                    attribute :>> isUnique = false; 
                                    ref allocation '6f1e7d52-baab-4d9a-a0aa-d1668e86b5c4' : PortAllocation
                                        allocate allocatedPort ::> 'Physical Functions'::'Root Physical Function'.'Store H Fluid'.'FOP 1'
                                        to allocatingPort ::> 'CP 2'; 
                                    ref :>> ownedPortAllocations =  ('6f1e7d52-baab-4d9a-a0aa-d1668e86b5c4'); 
                                     
                                }  
                                port 'CP 3' : ComponentPort { 
                                    @CapellaID { eid = "44d25575-7afe-480e-8325-1856b217454a"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::OUT; 
                                    attribute :>> isUnique = false; 
                                    ref allocation '9e3265dc-b31a-4e69-8e46-4a906448b550' : PortAllocation
                                        allocate allocatedPort ::> 'Physical Functions'::'Root Physical Function'.'Store H Fluid'.'FOP 2'
                                        to allocatingPort ::> 'CP 3'; 
                                    ref :>> ownedPortAllocations =  ('9e3265dc-b31a-4e69-8e46-4a906448b550'); 
                                     
                                }  
                                port 'CP 4' : ComponentPort { 
                                    @CapellaID { eid = "7a7a43f3-c8b8-4b97-b3d3-c02be00b9526"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '3d4aaa38-8d95-4d62-9885-b694b3968688' : PortAllocation
                                        allocate allocatedPort ::> 'Physical Functions'::'Root Physical Function'.'Store H Fluid'.'FIP 1'
                                        to allocatingPort ::> 'CP 4'; 
                                    ref :>> ownedPortAllocations =  ('3d4aaa38-8d95-4d62-9885-b694b3968688'); 
                                     
                                }  
                                ref :>> ownedFunctionalAllocation =  ('6b61e820-3f4d-423e-9ebb-515503a34561'); 
                                 
                            }  
                            part 'Junction' : PhysicalComponent { 
                                @CapellaID { eid = "adb1b5df-7340-416b-8ecd-756e9a3345de"; } 
                                attribute :>> isAbstract = false; 
                                attribute :>> isActor = false; 
                                attribute :>> isHuman = false; 
                                attribute :>> kind = PhysicalComponentKind::UNSET; 
                                attribute :>> nature = PhysicalComponentNature::BEHAVIOR; 
                                allocation '4afe3f60-c28f-421a-8cef-b42174fa3810' : ComponentFunctionalAllocation
                                    allocate function ::> 'Physical Functions'::'Root Physical Function'.'Channel'
                                    to component ::> 'Junction' { 
                                    @CapellaID { eid = "4afe3f60-c28f-421a-8cef-b42174fa3810"; sid = "4afe3f60-c28f-421a-8cef-b42174fa3810"; } 
                                     
                                } 
                                perform 'Physical Functions'::'Root Physical Function'.'Channel' ; 
                                port 'CP 1' : ComponentPort { 
                                    @CapellaID { eid = "53d4c5d4-d3d9-406b-b9a4-521b5c50bd6d"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '1a903bde-c591-4275-b359-3935aeccabc4' : PortAllocation
                                        allocate allocatedPort ::> 'Physical Functions'::'Root Physical Function'.'Channel'.'FIP 2'
                                        to allocatingPort ::> 'CP 1'; 
                                    ref :>> ownedPortAllocations =  ('1a903bde-c591-4275-b359-3935aeccabc4'); 
                                     
                                }  
                                port 'CP 2' : ComponentPort { 
                                    @CapellaID { eid = "967bd559-e99a-4216-9550-f31239137ae8"; sid = "967bd559-e99a-4216-9550-f31239137ae8"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::OUT; 
                                    attribute :>> isUnique = false; 
                                    ref allocation '730f352e-d6dd-4c1d-bccf-d4973b81af8d' : PortAllocation
                                        allocate allocatedPort ::> 'Physical Functions'::'Root Physical Function'.'Channel'.'FOP 1'
                                        to allocatingPort ::> 'CP 2'; 
                                    ref :>> ownedPortAllocations =  ('730f352e-d6dd-4c1d-bccf-d4973b81af8d'); 
                                     
                                }  
                                ref :>> ownedFunctionalAllocation =  ('4afe3f60-c28f-421a-8cef-b42174fa3810'); 
                                 
                            }  
                            part 'Selector Valve' : PhysicalComponent { 
                                @CapellaID { eid = "a12aefc5-08a9-4170-9a72-8e9589be4b93"; } 
                                attribute :>> isAbstract = false; 
                                attribute :>> isActor = false; 
                                attribute :>> isHuman = false; 
                                attribute :>> kind = PhysicalComponentKind::UNSET; 
                                attribute :>> nature = PhysicalComponentNature::BEHAVIOR; 
                                allocation '06f0b873-f684-4c56-976d-1aa55a2e7268' : ComponentFunctionalAllocation
                                    allocate function ::> 'Physical Functions'::'Root Physical Function'.'Control'
                                    to component ::> 'Selector Valve' { 
                                    @CapellaID { eid = "06f0b873-f684-4c56-976d-1aa55a2e7268"; } 
                                     
                                } 
                                perform 'Physical Functions'::'Root Physical Function'.'Control' ; 
                                port 'CP 1' : ComponentPort { 
                                    @CapellaID { eid = "d1bef554-4a33-4523-a722-ea522602823f"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation 'c6cfe42c-eb2d-4534-b6fe-bfdb27c17d72' : PortAllocation
                                        allocate allocatedPort ::> 'Physical Functions'::'Root Physical Function'.'Control'.'FIP 1'
                                        to allocatingPort ::> 'CP 1'; 
                                    ref :>> ownedPortAllocations =  ('c6cfe42c-eb2d-4534-b6fe-bfdb27c17d72'); 
                                     
                                }  
                                port 'CP 2' : ComponentPort { 
                                    @CapellaID { eid = "896ec2fb-2b82-4714-bcdc-ccdac3c4bb29"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '35f30189-9a85-40c5-85e3-b008e4f13463' : PortAllocation
                                        allocate allocatedPort ::> 'Physical Functions'::'Root Physical Function'.'Control'.'FIP 2'
                                        to allocatingPort ::> 'CP 2'; 
                                    ref :>> ownedPortAllocations =  ('35f30189-9a85-40c5-85e3-b008e4f13463'); 
                                     
                                }  
                                port 'CP 3' : ComponentPort { 
                                    @CapellaID { eid = "9037db30-9e4a-4684-b291-b112af9c3f46"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::OUT; 
                                    attribute :>> isUnique = false; 
                                    ref allocation '56589bcd-f8f1-4600-a9ba-0077b6303a61' : PortAllocation
                                        allocate allocatedPort ::> 'Physical Functions'::'Root Physical Function'.'Control'.'FOP 1'
                                        to allocatingPort ::> 'CP 3'; 
                                    ref :>> ownedPortAllocations =  ('56589bcd-f8f1-4600-a9ba-0077b6303a61'); 
                                     
                                }  
                                ref :>> ownedFunctionalAllocation =  ('06f0b873-f684-4c56-976d-1aa55a2e7268'); 
                                 
                            }  
                            part 'Audio' : PhysicalComponent { 
                                @CapellaID { eid = "fd25cfd0-17af-4e78-a26e-f18e121ce08c"; sid = "fd25cfd0-17af-4e78-a26e-f18e121ce08c"; } 
                                attribute :>> isAbstract = false; 
                                attribute :>> isActor = false; 
                                attribute :>> isHuman = false; 
                                attribute :>> kind = PhysicalComponentKind::UNSET; 
                                attribute :>> nature = PhysicalComponentNature::BEHAVIOR; 
                                 
                            }  
                            part 'MC Comp' : PhysicalComponent { 
                                @CapellaID { eid = "cbb484d9-d5f4-4116-a006-42ee56fba414"; sid = "cbb484d9-d5f4-4116-a006-42ee56fba414"; } 
                                attribute :>> isAbstract = false; 
                                attribute :>> isActor = false; 
                                attribute :>> isHuman = false; 
                                attribute :>> kind = PhysicalComponentKind::UNSET; 
                                attribute :>> nature = PhysicalComponentNature::BEHAVIOR; 
                                allocation '48cd6385-deab-4950-b57a-7e5d4ad53507' : ComponentFunctionalAllocation
                                    allocate function ::> 'Physical Functions'::'Root Physical Function'.'Perform Overflight Recon Mission'.'Perform Scan'
                                    to component ::> 'MC Comp' { 
                                    @CapellaID { eid = "48cd6385-deab-4950-b57a-7e5d4ad53507"; sid = "48cd6385-deab-4950-b57a-7e5d4ad53507"; } 
                                     
                                } 
                                perform 'Physical Functions'::'Root Physical Function'.'Perform Overflight Recon Mission'.'Perform Scan' ; 
                                port 'CP 1' : ComponentPort { 
                                    @CapellaID { eid = "4af220a1-4178-48dd-a7b9-d5af83087b30"; sid = "4af220a1-4178-48dd-a7b9-d5af83087b30"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::OUT; 
                                    attribute :>> isUnique = false; 
                                    ref allocation 'cda5bfd4-ed83-46e6-b062-6be28d4e1110' : PortAllocation
                                        allocate allocatedPort ::> 'Physical Functions'::'Root Physical Function'.'Perform Overflight Recon Mission'.'Perform Scan'.'FOP 1'
                                        to allocatingPort ::> 'CP 1'; 
                                    ref :>> ownedPortAllocations =  ('cda5bfd4-ed83-46e6-b062-6be28d4e1110'); 
                                     
                                }  
                                ref :>> ownedFunctionalAllocation =  ('48cd6385-deab-4950-b57a-7e5d4ad53507'); 
                                 
                            }  
                            part 'NLG Door' : PhysicalComponent { 
                                @CapellaID { eid = "c6f2151c-2357-4aa3-a44f-80b5bab5ed32"; } 
                                attribute :>> isAbstract = false; 
                                attribute :>> isActor = false; 
                                attribute :>> isHuman = false; 
                                attribute :>> kind = PhysicalComponentKind::UNSET; 
                                attribute :>> nature = PhysicalComponentNature::BEHAVIOR; 
                                allocation '620a7d5b-00af-4698-8ada-ae63610f2719' : ComponentFunctionalAllocation
                                    allocate function ::> 'Physical Functions'::'Root Physical Function'.'Open and Close'
                                    to component ::> 'NLG Door' { 
                                    @CapellaID { eid = "620a7d5b-00af-4698-8ada-ae63610f2719"; } 
                                     
                                } 
                                perform 'Physical Functions'::'Root Physical Function'.'Open and Close' ; 
                                port 'CP 1' : ComponentPort { 
                                    @CapellaID { eid = "9c433458-ae47-4f73-8c36-b39e20bb7768"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '6773bbf9-48a1-4511-8449-20fefa4b8374' : PortAllocation
                                        allocate allocatedPort ::> 'Physical Functions'::'Root Physical Function'.'Open and Close'.'FIP 1'
                                        to allocatingPort ::> 'CP 1'; 
                                    ref :>> ownedPortAllocations =  ('6773bbf9-48a1-4511-8449-20fefa4b8374'); 
                                     
                                }  
                                port 'CP 2' : ComponentPort { 
                                    @CapellaID { eid = "8e00307b-86de-47fd-930a-e9de8dd104d2"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '888e07e0-e189-446b-a49d-b1cfd9623757' : PortAllocation
                                        allocate allocatedPort ::> 'Physical Functions'::'Root Physical Function'.'Open and Close'.'FIP 2'
                                        to allocatingPort ::> 'CP 2'; 
                                    ref :>> ownedPortAllocations =  ('888e07e0-e189-446b-a49d-b1cfd9623757'); 
                                     
                                }  
                                ref :>> ownedFunctionalAllocation =  ('620a7d5b-00af-4698-8ada-ae63610f2719'); 
                                 
                            }  
                            part 'Firm' : PhysicalComponent { 
                                @CapellaID { eid = "aebfc22e-7093-43f0-a3b3-0aad47a60655"; } 
                                attribute :>> isAbstract = false; 
                                attribute :>> isActor = false; 
                                attribute :>> isHuman = false; 
                                attribute :>> kind = PhysicalComponentKind::FIRMWARE; 
                                attribute :>> nature = PhysicalComponentNature::BEHAVIOR; 
                                allocation 'f92f5a57-8087-496d-a34e-c81e55789493' : ComponentFunctionalAllocation
                                    allocate function ::> 'Physical Functions'::'Root Physical Function'.'PhysicalFunction 39'
                                    to component ::> 'Firm' { 
                                    @CapellaID { eid = "f92f5a57-8087-496d-a34e-c81e55789493"; } 
                                     
                                } 
                                perform 'Physical Functions'::'Root Physical Function'.'PhysicalFunction 39' ; 
                                ref :>> ownedFunctionalAllocation =  ('f92f5a57-8087-496d-a34e-c81e55789493'); 
                                 
                            }  
                            part 'Dump Control' : PhysicalComponent { 
                                @CapellaID { eid = "986c37a6-ef82-4401-949a-d5b1b076bae3"; } 
                                attribute :>> isAbstract = false; 
                                attribute :>> isActor = false; 
                                attribute :>> isHuman = false; 
                                attribute :>> kind = PhysicalComponentKind::UNSET; 
                                attribute :>> nature = PhysicalComponentNature::BEHAVIOR; 
                                allocation '0e0683b5-12ac-439d-b9ea-7365b7d0d3cd' : ComponentFunctionalAllocation
                                    allocate function ::> 'Physical Functions'::'Root Physical Function'.'NLG Dump'
                                    to component ::> 'Dump Control' { 
                                    @CapellaID { eid = "0e0683b5-12ac-439d-b9ea-7365b7d0d3cd"; } 
                                     
                                } 
                                perform 'Physical Functions'::'Root Physical Function'.'NLG Dump' ; 
                                allocation 'b7931ad0-d2d4-4668-a435-93e32f513942' : ComponentFunctionalAllocation
                                    allocate function ::> 'Physical Functions'::'Root Physical Function'.'NLG Door Dump'
                                    to component ::> 'Dump Control' { 
                                    @CapellaID { eid = "b7931ad0-d2d4-4668-a435-93e32f513942"; } 
                                     
                                } 
                                perform 'Physical Functions'::'Root Physical Function'.'NLG Door Dump' ; 
                                port 'CP 1' : ComponentPort { 
                                    @CapellaID { eid = "1d3d59e3-65df-4aab-8098-a0c33fecde67"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '745c4e3f-bd7d-4ff7-9d2c-a9d0ac3960a6' : PortAllocation
                                        allocate allocatedPort ::> 'Physical Functions'::'Root Physical Function'.'NLG Door Dump'.'FIP 1'
                                        to allocatingPort ::> 'CP 1'; 
                                    ref :>> ownedPortAllocations =  ('745c4e3f-bd7d-4ff7-9d2c-a9d0ac3960a6'); 
                                     
                                }  
                                port 'CP 2' : ComponentPort { 
                                    @CapellaID { eid = "1c0a9344-00aa-4226-b112-90c39aabf5e7"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '95b4b9ff-1da9-496a-8365-b794eea7582c' : PortAllocation
                                        allocate allocatedPort ::> 'Physical Functions'::'Root Physical Function'.'NLG Dump'.'FIP 1'
                                        to allocatingPort ::> 'CP 2'; 
                                    ref :>> ownedPortAllocations =  ('95b4b9ff-1da9-496a-8365-b794eea7582c'); 
                                     
                                }  
                                port 'CP 3' : ComponentPort { 
                                    @CapellaID { eid = "28f0caab-0f74-4b00-a5a3-36c1518fc0ba"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::OUT; 
                                    attribute :>> isUnique = false; 
                                    ref allocation 'bb53f712-148a-42ff-a7f0-c12993382366' : PortAllocation
                                        allocate allocatedPort ::> 'Physical Functions'::'Root Physical Function'.'NLG Door Dump'.'FOP 1'
                                        to allocatingPort ::> 'CP 3'; 
                                    ref :>> ownedPortAllocations =  ('bb53f712-148a-42ff-a7f0-c12993382366'); 
                                     
                                }  
                                port 'CP 4' : ComponentPort { 
                                    @CapellaID { eid = "6685509d-07f2-46e3-9ff1-72da40490be8"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::OUT; 
                                    attribute :>> isUnique = false; 
                                    ref allocation '99ac2e5b-0aff-4d36-8f3a-bd9dba88331f' : PortAllocation
                                        allocate allocatedPort ::> 'Physical Functions'::'Root Physical Function'.'NLG Dump'.'FOP 1'
                                        to allocatingPort ::> 'CP 4'; 
                                    ref :>> ownedPortAllocations =  ('99ac2e5b-0aff-4d36-8f3a-bd9dba88331f'); 
                                     
                                }  
                                ref :>> ownedFunctionalAllocation =  ('0e0683b5-12ac-439d-b9ea-7365b7d0d3cd',
                                'b7931ad0-d2d4-4668-a435-93e32f513942'); 
                                 
                            }  
                            part 'Accumulator' : PhysicalComponent { 
                                @CapellaID { eid = "d8e71943-4e61-4855-943b-c24b9bb0067c"; } 
                                attribute :>> isAbstract = false; 
                                attribute :>> isActor = false; 
                                attribute :>> isHuman = false; 
                                attribute :>> kind = PhysicalComponentKind::UNSET; 
                                attribute :>> nature = PhysicalComponentNature::BEHAVIOR; 
                                allocation '9c7f3e49-b1a2-4534-a602-bba0b6df3e67' : ComponentFunctionalAllocation
                                    allocate function ::> 'Physical Functions'::'Root Physical Function'.'Store'
                                    to component ::> 'Accumulator' { 
                                    @CapellaID { eid = "9c7f3e49-b1a2-4534-a602-bba0b6df3e67"; } 
                                     
                                } 
                                perform 'Physical Functions'::'Root Physical Function'.'Store' ; 
                                allocation '4b2f80d4-490e-4aa2-9fc7-9dedd9e2bf5f' : ComponentFunctionalAllocation
                                    allocate function ::> 'Physical Functions'::'Root Physical Function'.'Maintain Pressure'
                                    to component ::> 'Accumulator' { 
                                    @CapellaID { eid = "4b2f80d4-490e-4aa2-9fc7-9dedd9e2bf5f"; } 
                                     
                                } 
                                perform 'Physical Functions'::'Root Physical Function'.'Maintain Pressure' ; 
                                ref :>> ownedFunctionalAllocation =  ('9c7f3e49-b1a2-4534-a602-bba0b6df3e67',
                                '4b2f80d4-490e-4aa2-9fc7-9dedd9e2bf5f'); 
                                 
                            }  
                            part 'FLIR' : PhysicalComponent { 
                                @CapellaID { eid = "b21daaf3-da62-4ed0-b5f9-f24a6c822024"; sid = "b21daaf3-da62-4ed0-b5f9-f24a6c822024"; } 
                                attribute :>> isAbstract = false; 
                                attribute :>> isActor = false; 
                                attribute :>> isHuman = false; 
                                attribute :>> kind = PhysicalComponentKind::UNSET; 
                                attribute :>> nature = PhysicalComponentNature::BEHAVIOR; 
                                allocation 'e132df09-2a52-46f9-ad13-778bcb5ff4c6' : ComponentFunctionalAllocation
                                    allocate function ::> 'Physical Functions'::'Root Physical Function'.'Capture Video'
                                    to component ::> 'FLIR' { 
                                    @CapellaID { eid = "e132df09-2a52-46f9-ad13-778bcb5ff4c6"; sid = "e132df09-2a52-46f9-ad13-778bcb5ff4c6"; } 
                                     
                                } 
                                perform 'Physical Functions'::'Root Physical Function'.'Capture Video' ; 
                                allocation 'bbaeefa2-97f7-4170-95d6-6f9669b54be6' : ComponentFunctionalAllocation
                                    allocate function ::> 'Physical Functions'::'Root Physical Function'.'Capture Photos'
                                    to component ::> 'FLIR' { 
                                    @CapellaID { eid = "bbaeefa2-97f7-4170-95d6-6f9669b54be6"; sid = "bbaeefa2-97f7-4170-95d6-6f9669b54be6"; } 
                                     
                                } 
                                perform 'Physical Functions'::'Root Physical Function'.'Capture Photos' ; 
                                port 'CP 1' : ComponentPort { 
                                    @CapellaID { eid = "deb2eecd-279a-4845-bade-9ded307c0b41"; sid = "deb2eecd-279a-4845-bade-9ded307c0b41"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::OUT; 
                                    attribute :>> isUnique = false; 
                                    ref allocation '28fd6075-f3b7-4f91-ae42-ef871bf388c8' : PortAllocation
                                        allocate allocatedPort ::> 'Physical Functions'::'Root Physical Function'.'Capture Video'.'outVideo'
                                        to allocatingPort ::> 'CP 1'; 
                                    ref allocation '7ba4bf85-d10d-4d7b-a273-c6a50422f6c7' : PortAllocation
                                        allocate allocatedPort ::> 'Physical Functions'::'Root Physical Function'.'Capture Photos'.'outPhotos'
                                        to allocatingPort ::> 'CP 1'; 
                                    ref allocation 'b2e2e5c2-373e-42ef-aabc-5bae06df2107' : PortAllocation
                                        allocate allocatedPort ::> 'Physical Functions'::'Root Physical Function'.'Capture Video'.'FIP 3'
                                        to allocatingPort ::> 'CP 1'; 
                                    ref allocation '05c66170-1a93-47ab-bace-53b8556582f9' : PortAllocation
                                        allocate allocatedPort ::> 'Physical Functions'::'Root Physical Function'.'Capture Photos'.'FIP 2'
                                        to allocatingPort ::> 'CP 1'; 
                                    ref :>> ownedPortAllocations =  ('28fd6075-f3b7-4f91-ae42-ef871bf388c8',
                                    '7ba4bf85-d10d-4d7b-a273-c6a50422f6c7',
                                    'b2e2e5c2-373e-42ef-aabc-5bae06df2107',
                                    '05c66170-1a93-47ab-bace-53b8556582f9'); 
                                     
                                }  
                                port 'CP 2' : ComponentPort { 
                                    @CapellaID { eid = "652e8919-713f-4bc8-b34f-748876abd176"; sid = "652e8919-713f-4bc8-b34f-748876abd176"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '0136a9fa-dc33-4634-a0e9-a831a72d872f' : PortAllocation
                                        allocate allocatedPort ::> 'Physical Functions'::'Root Physical Function'.'Capture Photos'.'inImage'
                                        to allocatingPort ::> 'CP 2'; 
                                    ref allocation '5b7b89a5-8560-483b-be8c-60a83a8fe5ce' : PortAllocation
                                        allocate allocatedPort ::> 'Physical Functions'::'Root Physical Function'.'Capture Video'.'inAudio Visual'
                                        to allocatingPort ::> 'CP 2'; 
                                    ref :>> ownedPortAllocations =  ('0136a9fa-dc33-4634-a0e9-a831a72d872f',
                                    '5b7b89a5-8560-483b-be8c-60a83a8fe5ce'); 
                                     
                                }  
                                port 'CP 3' : ComponentPort { 
                                    @CapellaID { eid = "c2a25757-c2ab-4570-96af-56daf94acbab"; sid = "c2a25757-c2ab-4570-96af-56daf94acbab"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '14ff3d78-8eb1-43ad-a263-a03eb04b9c74' : PortAllocation
                                        allocate allocatedPort ::> 'Physical Functions'::'Root Physical Function'.'Capture Video'.'FIP 2'
                                        to allocatingPort ::> 'CP 3'; 
                                    ref :>> ownedPortAllocations =  ('14ff3d78-8eb1-43ad-a263-a03eb04b9c74'); 
                                     
                                }  
                                ref :>> ownedFunctionalAllocation =  ('e132df09-2a52-46f9-ad13-778bcb5ff4c6',
                                'bbaeefa2-97f7-4170-95d6-6f9669b54be6'); 
                                 
                            }  
                            part 'SW' : PhysicalComponent { 
                                @CapellaID { eid = "99ff57a4-713e-49c3-ae32-b353f75e3b80"; } 
                                attribute :>> isAbstract = false; 
                                attribute :>> isActor = false; 
                                attribute :>> isHuman = false; 
                                attribute :>> kind = PhysicalComponentKind::SOFTWARE; 
                                attribute :>> nature = PhysicalComponentNature::BEHAVIOR; 
                                allocation '7944ca9b-bcb6-4dbf-b691-d86a9e4bcd13' : ComponentFunctionalAllocation
                                    allocate function ::> 'Physical Functions'::'Root Physical Function'.'PhysicalFunction 40'
                                    to component ::> 'SW' { 
                                    @CapellaID { eid = "7944ca9b-bcb6-4dbf-b691-d86a9e4bcd13"; } 
                                     
                                } 
                                perform 'Physical Functions'::'Root Physical Function'.'PhysicalFunction 40' ; 
                                ref :>> ownedFunctionalAllocation =  ('7944ca9b-bcb6-4dbf-b691-d86a9e4bcd13'); 
                                 
                            }  
                            part 'Hydrualic Controls' : PhysicalComponent { 
                                @CapellaID { eid = "f7672b45-fcad-446a-8076-de3b389256b8"; sid = "f7672b45-fcad-446a-8076-de3b389256b8"; } 
                                attribute :>> isAbstract = false; 
                                attribute :>> isActor = false; 
                                attribute :>> isHuman = false; 
                                attribute :>> kind = PhysicalComponentKind::UNSET; 
                                attribute :>> nature = PhysicalComponentNature::BEHAVIOR; 
                                 
                            }  
                            part 'Green Hydaulic Pump' : PhysicalComponent { 
                                @CapellaID { eid = "5cc4b0f3-422b-47be-8ffd-3adaae4204d2"; } 
                                attribute :>> isAbstract = false; 
                                attribute :>> isActor = false; 
                                attribute :>> isHuman = false; 
                                attribute :>> kind = PhysicalComponentKind::UNSET; 
                                attribute :>> nature = PhysicalComponentNature::BEHAVIOR; 
                                allocation 'e06ceb7a-31c7-481c-9d0c-f25c724b8b0b' : ComponentFunctionalAllocation
                                    allocate function ::> 'Physical Functions'::'Root Physical Function'.'Pump Fliud'
                                    to component ::> 'Green Hydaulic Pump' { 
                                    @CapellaID { eid = "e06ceb7a-31c7-481c-9d0c-f25c724b8b0b"; } 
                                     
                                } 
                                perform 'Physical Functions'::'Root Physical Function'.'Pump Fliud' ; 
                                port 'CP 1' : ComponentPort { 
                                    @CapellaID { eid = "5fc6de3c-d859-4fad-91cf-500e33068193"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation 'cd4234b9-6246-4391-999d-56f2decfb905' : PortAllocation
                                        allocate allocatedPort ::> 'Physical Functions'::'Root Physical Function'.'Pump Fliud'.'FIP 1'
                                        to allocatingPort ::> 'CP 1'; 
                                    ref :>> ownedPortAllocations =  ('cd4234b9-6246-4391-999d-56f2decfb905'); 
                                     
                                }  
                                port 'CP 2' : ComponentPort { 
                                    @CapellaID { eid = "4da19b1d-c072-43b6-8418-2f7443451551"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::OUT; 
                                    attribute :>> isUnique = false; 
                                     
                                }  
                                ref :>> ownedFunctionalAllocation =  ('e06ceb7a-31c7-481c-9d0c-f25c724b8b0b'); 
                                 
                            }  
                            part 'H2' : PhysicalComponent { 
                                @CapellaID { eid = "c8f54838-76f6-4f2a-a8a5-bf4aa0665e0d"; } 
                                attribute :>> isAbstract = false; 
                                attribute :>> isActor = false; 
                                attribute :>> isHuman = false; 
                                attribute :>> kind = PhysicalComponentKind::UNSET; 
                                attribute :>> nature = PhysicalComponentNature::BEHAVIOR; 
                                allocation 'ad953ef3-945f-49cc-b450-1e0282030b59' : ComponentFunctionalAllocation
                                    allocate function ::> 'Physical Functions'::'Root Physical Function'.'Supply Pressure'
                                    to component ::> 'H2' { 
                                    @CapellaID { eid = "ad953ef3-945f-49cc-b450-1e0282030b59"; sid = "ad953ef3-945f-49cc-b450-1e0282030b59"; } 
                                     
                                } 
                                perform 'Physical Functions'::'Root Physical Function'.'Supply Pressure' ; 
                                port 'CP 1' : ComponentPort { 
                                    @CapellaID { eid = "685e2833-a5c5-4c3a-bcc8-fa024c4ce472"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation '0351fb8b-8706-4470-8fbd-6d9b2f163834' : PortAllocation
                                        allocate allocatedPort ::> 'Physical Functions'::'Root Physical Function'.'Supply Pressure'.'FIP 2'
                                        to allocatingPort ::> 'CP 1'; 
                                    ref :>> ownedPortAllocations =  ('0351fb8b-8706-4470-8fbd-6d9b2f163834'); 
                                     
                                }  
                                port 'CP 2' : ComponentPort { 
                                    @CapellaID { eid = "3ff1ee49-b928-48d5-a019-629514ca6527"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref allocation 'ebfee347-ce76-4930-947e-3ef1d381fc03' : PortAllocation
                                        allocate allocatedPort ::> 'Physical Functions'::'Root Physical Function'.'Supply Pressure'.'FIP 1'
                                        to allocatingPort ::> 'CP 2'; 
                                    ref :>> ownedPortAllocations =  ('ebfee347-ce76-4930-947e-3ef1d381fc03'); 
                                     
                                }  
                                ref :>> ownedFunctionalAllocation =  ('ad953ef3-945f-49cc-b450-1e0282030b59'); 
                                 
                            }  
                            ref :>> ownedFunctionalAllocation =  ('a657f31a-0620-43d7-8b73-9c09e1d7b90b'); 
                            ref :>> ownedComponentExchanges =  ('3d2d91ab-6561-4b93-ac31-4cb688f46b8a'); 
                             
                             
                            ref :>> ownedPhysicalComponents =  ('ORS ',
                            'H R',
                            'Junction',
                            'Selector Valve',
                            'Audio',
                            'MC Comp',
                            'NLG Door',
                            'Firm',
                            'Dump Control',
                            'Accumulator',
                            'FLIR',
                            'SW',
                            'Hydrualic Controls',
                            'Green Hydaulic Pump',
                            'H2'); 
                        }  
                        part 'Pressured Hydraulic' : PhysicalComponent { 
                            @CapellaID { eid = "1a003591-19a6-4cb2-8a0a-2f2bb0c47b6d"; sid = "1a003591-19a6-4cb2-8a0a-2f2bb0c47b6d"; } 
                            attribute :>> isAbstract = false; 
                            attribute :>> isActor = false; 
                            attribute :>> isHuman = false; 
                            attribute :>> kind = PhysicalComponentKind::UNSET; 
                            attribute :>> nature = PhysicalComponentNature::BEHAVIOR; 
                            allocation 'c52bb8bc-c091-411c-97ab-e57f0f538a4d' : ComponentFunctionalAllocation
                                allocate function ::> 'Physical Functions'::'Root Physical Function'.'SupplyPressur'
                                to component ::> 'Pressured Hydraulic' { 
                                @CapellaID { eid = "c52bb8bc-c091-411c-97ab-e57f0f538a4d"; sid = "c52bb8bc-c091-411c-97ab-e57f0f538a4d"; } 
                                 
                            } 
                            perform 'Physical Functions'::'Root Physical Function'.'SupplyPressur' ; 
                            port 'CP 1' : ComponentPort { 
                                @CapellaID { eid = "74bafd25-8dc7-4a07-b2e5-1223dd300e0a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation '0deb825e-faaf-4285-a4c9-ceb358b47426' : PortAllocation
                                    allocate allocatedPort ::> 'Physical Functions'::'Root Physical Function'.'SupplyPressur'.'FIP 2'
                                    to allocatingPort ::> 'CP 1'; 
                                ref :>> ownedPortAllocations =  ('0deb825e-faaf-4285-a4c9-ceb358b47426'); 
                                 
                            }  
                            port 'CP 2' : ComponentPort { 
                                @CapellaID { eid = "a9639c34-8ae4-4e38-90de-2868d8cbe8fc"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation 'e6d036fa-6dfc-4d83-bece-863996a66088' : PortAllocation
                                    allocate allocatedPort ::> 'Physical Functions'::'Root Physical Function'.'SupplyPressur'.'FOP 5'
                                    to allocatingPort ::> 'CP 2'; 
                                ref :>> ownedPortAllocations =  ('e6d036fa-6dfc-4d83-bece-863996a66088'); 
                                 
                            }  
                            port 'CP 3' : ComponentPort { 
                                @CapellaID { eid = "968f89ad-1241-4c31-a518-a6b3e3568f65"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '078d971f-df47-48bc-aba9-6b083a57e530' : PortAllocation
                                    allocate allocatedPort ::> 'Physical Functions'::'Root Physical Function'.'SupplyPressur'.'FOP 8'
                                    to allocatingPort ::> 'CP 3'; 
                                ref :>> ownedPortAllocations =  ('078d971f-df47-48bc-aba9-6b083a57e530'); 
                                 
                            }  
                            ref :>> ownedFunctionalAllocation =  ('c52bb8bc-c091-411c-97ab-e57f0f538a4d'); 
                             
                        }  
                        part 'HR' : PhysicalComponent { 
                            @CapellaID { eid = "eb4cadca-c4d3-41fe-9758-9b50d348b399"; } 
                            attribute :>> isAbstract = false; 
                            attribute :>> isActor = false; 
                            attribute :>> isHuman = false; 
                            attribute :>> kind = PhysicalComponentKind::UNSET; 
                            attribute :>> nature = PhysicalComponentNature::BEHAVIOR; 
                             
                        }  
                        part 'ComLink' : PhysicalComponent { 
                            @CapellaID { eid = "025dc7b0-d1a2-4953-9af0-056eb77bf379"; sid = "025dc7b0-d1a2-4953-9af0-056eb77bf379"; } 
                            attribute :>> isAbstract = false; 
                            attribute :>> isActor = false; 
                            attribute :>> isHuman = false; 
                            attribute :>> kind = PhysicalComponentKind::UNSET; 
                            attribute :>> nature = PhysicalComponentNature::BEHAVIOR; 
                            allocation '5cb0e752-eaad-48ab-b054-7f0d89b80314' : ComponentFunctionalAllocation
                                allocate function ::> 'Physical Functions'::'Root Physical Function'.'Relay to Operator'
                                to component ::> 'ComLink' { 
                                @CapellaID { eid = "5cb0e752-eaad-48ab-b054-7f0d89b80314"; sid = "5cb0e752-eaad-48ab-b054-7f0d89b80314"; } 
                                 
                            } 
                            perform 'Physical Functions'::'Root Physical Function'.'Relay to Operator' ; 
                            allocation '0ea2c5f0-17f4-4ff3-9c26-a36084551b2d' : ComponentFunctionalAllocation
                                allocate function ::> 'Physical Functions'::'Root Physical Function'.'Relay Overflight Data from Drone Mission'
                                to component ::> 'ComLink' { 
                                @CapellaID { eid = "0ea2c5f0-17f4-4ff3-9c26-a36084551b2d"; sid = "0ea2c5f0-17f4-4ff3-9c26-a36084551b2d"; } 
                                 
                            } 
                            perform 'Physical Functions'::'Root Physical Function'.'Relay Overflight Data from Drone Mission' ; 
                            port 'CP 1' : ComponentPort { 
                                @CapellaID { eid = "11f662c0-8a85-4621-9ae6-1ed4d4e689fb"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref allocation '0d9d6200-5510-47c2-96d2-555f4137f90f' : PortAllocation
                                    allocate allocatedPort ::> 'Physical Functions'::'Root Physical Function'.'Relay Overflight Data from Drone Mission'.'outRecon Overflight Data'
                                    to allocatingPort ::> 'CP 1'; 
                                ref :>> ownedPortAllocations =  ('0d9d6200-5510-47c2-96d2-555f4137f90f'); 
                                 
                            }  
                            port 'CP 2' : ComponentPort { 
                                @CapellaID { eid = "e1f9db24-2f39-4a50-98db-41a9d8cc6f7f"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation '540aed8a-e0e8-48f4-b1cd-36cabb0a74db' : PortAllocation
                                    allocate allocatedPort ::> 'Physical Functions'::'Root Physical Function'.'Relay to Operator'.'FOP 1'
                                    to allocatingPort ::> 'CP 2'; 
                                ref :>> ownedPortAllocations =  ('540aed8a-e0e8-48f4-b1cd-36cabb0a74db'); 
                                 
                            }  
                            port 'CP 3' : ComponentPort { 
                                @CapellaID { eid = "a6bc21ca-2e7d-4e96-9f5f-d7b77b7fc036"; sid = "a6bc21ca-2e7d-4e96-9f5f-d7b77b7fc036"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref allocation 'b1ae3dd8-6481-42d3-8db2-691e7a36c90b' : PortAllocation
                                    allocate allocatedPort ::> 'Physical Functions'::'Root Physical Function'.'Relay Overflight Data from Drone Mission'.'inLocation'
                                    to allocatingPort ::> 'CP 3'; 
                                ref allocation '69dafa6b-3e6b-4e70-9cc8-7b4fd64548b8' : PortAllocation
                                    allocate allocatedPort ::> 'Physical Functions'::'Root Physical Function'.'Relay to Operator'.'FIP 2'
                                    to allocatingPort ::> 'CP 3'; 
                                ref allocation '05928dd4-8956-48eb-ac85-6fb8d77c2661' : PortAllocation
                                    allocate allocatedPort ::> 'Physical Functions'::'Root Physical Function'.'Relay Overflight Data from Drone Mission'.'FIP 2'
                                    to allocatingPort ::> 'CP 3'; 
                                ref :>> ownedPortAllocations =  ('b1ae3dd8-6481-42d3-8db2-691e7a36c90b',
                                '69dafa6b-3e6b-4e70-9cc8-7b4fd64548b8',
                                '05928dd4-8956-48eb-ac85-6fb8d77c2661'); 
                                 
                            }  
                            ref :>> ownedFunctionalAllocation =  ('5cb0e752-eaad-48ab-b054-7f0d89b80314',
                            '0ea2c5f0-17f4-4ff3-9c26-a36084551b2d'); 
                             
                        }  
                        ref :>> ownedComponentExchanges =  ('eab01e10-827a-421a-98fc-6aec6317df4f',
                        '3da72adf-d20a-4740-a964-39f4bc413126',
                        'c65b09b3-88ac-4f59-ba01-e2dfbd98092f',
                        'f024d824-6d61-4ea2-bd4a-f756f0ca019e',
                        '7ea77cc3-28bc-4e03-8364-e9ca89d9083e',
                        'c3caa067-07c8-4ac3-a5b8-7cd31d9cc04b',
                        '9d144b9e-1cd2-440b-a540-60b7a99884a2'); 
                         
                        ref :>> ownedPhysicalComponents =  ('NLG Downlock Sensor 2',
                        'NLG Dump Valve',
                        'NLG Doors Dump Valve',
                        'Weight on Wheel Sensor 1',
                        'NLG Wheel Steerin',
                        'NLG Uplock Sensor 1',
                        'NLG Door Actuator',
                        'NLG Struct Post',
                        'NLG Door Sensor',
                        'Airframe',
                        'NLG Shock',
                        'NLG  Control Valve',
                        'NLG Uplock Sensor 2',
                        'NLG Downlock Sensor 1',
                        'Weight on Wheelp Sensor 2',
                        'NLG Wheel',
                        'NLG Doors Selector Valve',
                        'Isolation Valve',
                        'Blue Hydraulic Pump',
                        'Shutoff Valve',
                        'Extension Retraction Lever',
                        'PC 40',
                        'NLG',
                        'H3',
                        'Fuel and Power System',
                        'Pressured Hydraulic',
                        'HR',
                        'ComLink'); 
                    }  
                    ref :>> ownedConstraints =  ('f09109dd-6312-4f29-9918-4aba8afa50af'); 
                    ref :>> ownedComponentExchanges =  ('9fa2ad25-5570-4ae7-a62c-d18729a78c4c',
                    'c04cefa7-1ebc-4db9-915f-effb64a09122',
                    '2e631237-b84b-4f27-b59b-42c6ec4fa809',
                    'd2728b32-bce4-48f2-a74b-5ec6e1461bb3',
                    'e6b14846-d38a-4ba4-9b16-54c3ad760e76',
                    'ab14a5c0-1ef4-450e-8b94-43c299476b40',
                    '15c2ccaf-6ff6-4697-915f-be6a9141728b',
                    'f82eef99-e3c8-4142-90ac-274d841119fc',
                    '1b52869b-3804-4e5c-9c22-723937f25edc',
                    'bfacc4d7-c2ca-427d-9750-51e82d3234c7',
                    '2627881e-1b24-458e-9423-13ab0016739a',
                    '62d8dd6a-ff5b-4df9-8c93-030c0c0a8617',
                    '64686ce1-271e-457e-890e-ef84e8b554f2',
                    '095ee5c0-51ed-49ec-a9d8-889202d0cf1c',
                    'f1bb9dfc-09ec-4e9c-a2a1-2594f694cc06',
                    'bc6ac1ab-600c-4c5b-8e07-f645eb8296c7',
                    '684fa9b7-b1b6-4bb2-be27-e6461fb9cbd8',
                    '9c229310-a429-4ba3-b497-3bc8ba12c21a',
                    'd8f1368f-1bf7-4788-b85a-7db80bc6814c',
                    '52cec165-5171-4290-b050-7c0c61e0004d',
                    '7b11072b-491a-4690-bad8-f845679271a2',
                    '35a702e1-ac98-4180-85ff-e18405633f49',
                    '16a559d3-a34a-4e83-a52b-4c5d265ce1ef',
                    'cbd135f0-e619-4859-ac05-95ec6622490e',
                    '60b22a4a-8789-4f62-8476-a67077e8dd97'); 
                     
                     
                    ref :>> ownedPhysicalLinks =  ('e6e7ba72-9242-40ce-bde0-d8993ec88345',
                    'a385361e-0e4b-462b-824c-f8368492c26a',
                    '5e36f45b-e114-47af-a75d-bf480e24c06d',
                    '9c2a5261-9743-49e8-9eb4-bf2a657193f1',
                    '7a43af87-5d93-45ac-b84e-ddc3dc698a23',
                    'f19804ff-4f9e-4391-bcf0-52e0fb021778',
                    'c245d353-cffe-4074-9340-9e4a1f8c97f9',
                    'af3272c2-9517-4446-8782-14d856630fdf',
                    'b349d104-4e67-4fcd-832b-a1219326ec5f',
                    '8a8e31ff-2b82-44bb-a81c-3dbcc3a24ad1',
                    '82fcee3b-38d7-4d08-baee-9cf9be22e5fc',
                    '8318ef2b-e36d-4da4-8fe5-44106d772bc7',
                    'b23e70fa-3b8a-4624-ad4f-057491f43f46',
                    'ca0dd27f-a1a9-4b74-8215-5719fe40b79f',
                    '395e6810-cffb-4919-8008-92f30f357ad7',
                    '96356375-49e5-4304-b22a-14a1cc1304e0',
                    'eedd256a-a3c4-450d-8ccb-db7369e4ba52',
                    '2b682a60-2255-4398-960e-b0efae8b171a',
                    'bdba5466-7d6a-4c30-beee-46bc7c9d14de',
                    'ba51e4b7-b4cd-4ddf-bcce-ebb357374da6',
                    'b9a7d908-2ac4-4aac-b1b5-a92e7086c454',
                    'fec5b940-e96a-422c-9a05-f0c7f34f6b9a',
                    'f418ca74-6ea7-4077-811d-71240598eac9',
                    '3b89e63d-6786-4c3f-8bc6-9632e01d2a43',
                    '36d6adb2-ee96-4e21-a0e7-f57a45031268',
                    'e4ec108d-73f8-4555-954d-076584588e01',
                    '6a6fcd77-7be5-4b5d-a460-7b232ccc5c12',
                    '2d927448-849b-48b6-ae7c-55167bfdede6',
                    '6ddfcfe7-a8b2-4252-9e11-cb6e309a9cdb',
                    '282e8334-5b1c-46f6-a1bf-2c467cb80c74',
                    '816058c7-de67-43f8-95b3-4b90d91e0929',
                    'e23c07ab-8745-4c18-a4cd-d3e8416e973b',
                    'f1e3cd51-e931-4b3d-b700-0127f9d4c160',
                    'a9948a56-74c0-4995-81e5-d2c98d932cf4',
                    '08832afb-1cd5-4e60-be8d-568ead6919ef',
                    'c8138675-339c-4feb-a1ae-06cd45a2b27e',
                    '10405803-2fc0-4274-8743-1356a041ff0d',
                    'e744dc5f-bfce-407c-bfe7-99ba2b2681cb',
                    '367c22c4-34dd-411b-9759-827ea0f57faa',
                    'da7523c5-bff4-4391-91ee-4a405df67805',
                    'e9a13f8c-dc13-470a-abbb-c545e5ab8fd3',
                    '4ef2f4af-a216-46f4-9225-d1e6a21cc536',
                    'f4fb3042-bbcb-4e55-95ae-e676e8dcb408',
                    'bc30689c-c382-4ea9-a33a-ac16501498ed',
                    'fdee7afb-3707-4375-a8f4-5cfbddb14d49'); 
                     
                    ref :>> ownedPhysicalComponents =  ('Aerial Platform',
                    'Ground System',
                    'Up Link',
                    'Satellite',
                    'Avionics',
                    'Vehicle Subsystems',
                    'Propulsion',
                    'Fuselage',
                    'Empennage',
                    'S Wing',
                    'P Wing',
                    'Drone',
                    'FLIR',
                    'Object Recognition System',
                    'COM LInk',
                    'Mission Computer',
                    'Braking System Control Unit (BSCU)',
                    'Hydralic Reservoir',
                    'Avionics Control',
                    'Braking Hydralulic Subsystem',
                    'Hydraulic ',
                    'Airframe',
                    'Data Bus 1',
                    'Bus 1',
                    'LGL Harness',
                    'Nose Landing Gear',
                    'Port Com Bus',
                    'NLG Door',
                    'H3',
                    'H2',
                    'H Reservoir',
                    'Pilot Interface',
                    'NLG Dump Valve',
                    'ion ',
                    'Behavior Parent'); 
                }  
                part 'Operator/Pilot' : PhysicalComponent { 
                    @CapellaID { eid = "b86ae229-e16f-435f-b5fb-89a04a6c6e83"; sid = "b86ae229-e16f-435f-b5fb-89a04a6c6e83"; } 
                    attribute :>> isAbstract = false; 
                    attribute :>> isActor = true; 
                    attribute :>> isHuman = true; 
                    attribute :>> kind = PhysicalComponentKind::UNSET; 
                    attribute :>> nature = PhysicalComponentNature::NODE; 
                    allocation '2f5f6884-289c-4d08-b057-0ade5c126910' : ComponentFunctionalAllocation
                        allocate function ::> 'Physical Functions'::'Root Physical Function'.'Provide C&amp;C SITREP'
                        to component ::> 'Structure'::'Operator/Pilot' { 
                        @CapellaID { eid = "2f5f6884-289c-4d08-b057-0ade5c126910"; sid = "2f5f6884-289c-4d08-b057-0ade5c126910"; } 
                         
                    } 
                    perform 'Physical Functions'::'Root Physical Function'.'Provide C&amp;C SITREP' ; 
                    allocation 'd00598a5-2d5f-4397-bd10-9adb594c2181' : ComponentFunctionalAllocation
                        allocate function ::> 'Physical Functions'::'Root Physical Function'.'Interpret SITREP'
                        to component ::> 'Structure'::'Operator/Pilot' { 
                        @CapellaID { eid = "d00598a5-2d5f-4397-bd10-9adb594c2181"; sid = "d00598a5-2d5f-4397-bd10-9adb594c2181"; } 
                         
                    } 
                    perform 'Physical Functions'::'Root Physical Function'.'Interpret SITREP' ; 
                    allocation 'c6650890-94b8-47a8-9704-b1325ee38f07' : ComponentFunctionalAllocation
                        allocate function ::> 'Physical Functions'::'Root Physical Function'.'Ad Hoc Mission Execution Update'
                        to component ::> 'Structure'::'Operator/Pilot' { 
                        @CapellaID { eid = "c6650890-94b8-47a8-9704-b1325ee38f07"; sid = "c6650890-94b8-47a8-9704-b1325ee38f07"; } 
                         
                    } 
                    perform 'Physical Functions'::'Root Physical Function'.'Ad Hoc Mission Execution Update' ; 
                    allocation 'cdd8c38c-f71d-4f28-9a59-207642fd3831' : ComponentFunctionalAllocation
                        allocate function ::> 'Physical Functions'::'Root Physical Function'.'Ad Hoc Mission Update Response'
                        to component ::> 'Structure'::'Operator/Pilot' { 
                        @CapellaID { eid = "cdd8c38c-f71d-4f28-9a59-207642fd3831"; sid = "cdd8c38c-f71d-4f28-9a59-207642fd3831"; } 
                         
                    } 
                    perform 'Physical Functions'::'Root Physical Function'.'Ad Hoc Mission Update Response' ; 
                    allocation '242fa93a-e70f-4a46-960a-1c1f874c3d54' : ComponentFunctionalAllocation
                        allocate function ::> 'Physical Functions'::'Root Physical Function'.'Support Response'
                        to component ::> 'Structure'::'Operator/Pilot' { 
                        @CapellaID { eid = "242fa93a-e70f-4a46-960a-1c1f874c3d54"; sid = "242fa93a-e70f-4a46-960a-1c1f874c3d54"; } 
                         
                    } 
                    perform 'Physical Functions'::'Root Physical Function'.'Support Response' ; 
                    allocation 'b6ea9ebb-5892-451e-98af-e32894877d6f' : ComponentFunctionalAllocation
                        allocate function ::> 'Physical Functions'::'Root Physical Function'.'Scan'
                        to component ::> 'Structure'::'Operator/Pilot' { 
                        @CapellaID { eid = "b6ea9ebb-5892-451e-98af-e32894877d6f"; sid = "b6ea9ebb-5892-451e-98af-e32894877d6f"; } 
                         
                    } 
                    perform 'Physical Functions'::'Root Physical Function'.'Scan' ; 
                    allocation '133ebbfa-7311-43c0-bf5e-798aa461b6ad' : ComponentFunctionalAllocation
                        allocate function ::> 'Physical Functions'::'Root Physical Function'.'Operator Mission Planning'
                        to component ::> 'Structure'::'Operator/Pilot' { 
                        @CapellaID { eid = "133ebbfa-7311-43c0-bf5e-798aa461b6ad"; sid = "133ebbfa-7311-43c0-bf5e-798aa461b6ad"; } 
                         
                    } 
                    perform 'Physical Functions'::'Root Physical Function'.'Operator Mission Planning' ; 
                    allocation 'a9994fea-eb14-4353-858a-ae7ab7a7cf74' : ComponentFunctionalAllocation
                        allocate function ::> 'Physical Functions'::'Root Physical Function'.'Control Gear'
                        to component ::> 'Structure'::'Operator/Pilot' { 
                        @CapellaID { eid = "a9994fea-eb14-4353-858a-ae7ab7a7cf74"; } 
                         
                    } 
                    perform 'Physical Functions'::'Root Physical Function'.'Control Gear' ; 
                    allocation '8a4ee225-5f52-4958-aeed-c96671a6e3bc' : ComponentFunctionalAllocation
                        allocate function ::> 'Physical Functions'::'Root Physical Function'.'NLG Gear Override'
                        to component ::> 'Structure'::'Operator/Pilot' { 
                        @CapellaID { eid = "8a4ee225-5f52-4958-aeed-c96671a6e3bc"; } 
                         
                    } 
                    perform 'Physical Functions'::'Root Physical Function'.'NLG Gear Override' ; 
                    allocation 'a14fba63-28ba-4b09-8144-5dfcaca7250f' : ComponentFunctionalAllocation
                        allocate function ::> 'Physical Functions'::'Root Physical Function'.'NLG Door Overide'
                        to component ::> 'Structure'::'Operator/Pilot' { 
                        @CapellaID { eid = "a14fba63-28ba-4b09-8144-5dfcaca7250f"; } 
                         
                    } 
                    perform 'Physical Functions'::'Root Physical Function'.'NLG Door Overide' ; 
                    port 'CP 1' : ComponentPort { 
                        @CapellaID { eid = "52c7e173-0a2f-4313-b2e1-282611dd1c1f"; sid = "52c7e173-0a2f-4313-b2e1-282611dd1c1f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                         
                    }  
                    port 'CP 2' : ComponentPort { 
                        @CapellaID { eid = "0fe99de9-a65e-4e5b-a32e-0aa174d5dc72"; sid = "0fe99de9-a65e-4e5b-a32e-0aa174d5dc72"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                         
                    }  
                    port 'PP 3' : PhysicalPort { 
                        @CapellaID { eid = "4339928e-9775-4310-9fd4-1ca9a86271ae"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    port 'CP 4' : ComponentPort { 
                        @CapellaID { eid = "a2c16f27-16af-4dad-b37e-a989da86b9df"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                        ref allocation 'a1a9da89-6327-4813-94c8-ed3149656f11' : PortAllocation
                            allocate allocatedPort ::> 'Physical Functions'::'Root Physical Function'.'Support Response'.'FIP 2'
                            to allocatingPort ::> 'CP 4'; 
                        ref :>> ownedPortAllocations =  ('a1a9da89-6327-4813-94c8-ed3149656f11'); 
                         
                    }  
                    port 'CP 5' : ComponentPort { 
                        @CapellaID { eid = "0090b28f-7703-48d3-b948-1212d11b1925"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                        ref allocation '61be43b3-30e1-49b2-8c0a-2f1b3c7919cb' : PortAllocation
                            allocate allocatedPort ::> 'Physical Functions'::'Root Physical Function'.'Operator Mission Planning'.'FIP 1'
                            to allocatingPort ::> 'CP 5'; 
                        ref allocation '73b71adf-b1fd-45b6-9c12-b58d696a7b4b' : PortAllocation
                            allocate allocatedPort ::> 'Physical Functions'::'Root Physical Function'.'Support Response'.'FOP 2'
                            to allocatingPort ::> 'CP 5'; 
                        ref :>> ownedPortAllocations =  ('61be43b3-30e1-49b2-8c0a-2f1b3c7919cb',
                        '73b71adf-b1fd-45b6-9c12-b58d696a7b4b'); 
                         
                    }  
                    port 'PP 6' : PhysicalPort { 
                        @CapellaID { eid = "a09f66be-92a5-4d6f-881e-44ca4664841d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    port 'PP 7' : PhysicalPort { 
                        @CapellaID { eid = "61d87b53-2a46-4937-99f4-4ded3ac87127"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    port 'PP 8' : PhysicalPort { 
                        @CapellaID { eid = "16645e6b-8413-4fd3-b0e7-f43bfa2fd86b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    port 'CP 9' : ComponentPort { 
                        @CapellaID { eid = "3923226f-d3f0-42be-842a-88d59d236e64"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                        ref allocation '6d284ed4-42a6-44f9-bb89-3e002eca1046' : PortAllocation
                            allocate allocatedPort ::> 'Physical Functions'::'Root Physical Function'.'Control Gear'.'FOP 1'
                            to allocatingPort ::> 'CP 9'; 
                        ref :>> ownedPortAllocations =  ('6d284ed4-42a6-44f9-bb89-3e002eca1046'); 
                         
                    }  
                    port 'CP 10' : ComponentPort { 
                        @CapellaID { eid = "292c0db9-6d3b-4387-b7b4-d1c69c508420"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                        ref allocation 'bf1a3950-078f-47f7-8630-ca52d2dfa86a' : PortAllocation
                            allocate allocatedPort ::> 'Physical Functions'::'Root Physical Function'.'NLG Door Overide'.'FOP 1'
                            to allocatingPort ::> 'CP 10'; 
                        ref :>> ownedPortAllocations =  ('bf1a3950-078f-47f7-8630-ca52d2dfa86a'); 
                         
                    }  
                    port 'CP 11' : ComponentPort { 
                        @CapellaID { eid = "704515a1-6f8c-4c53-aa95-822e0f81177e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                        ref allocation '79d9f8af-00e3-4b8f-a8da-cb940bb645ca' : PortAllocation
                            allocate allocatedPort ::> 'Physical Functions'::'Root Physical Function'.'NLG Gear Override'.'FOP 1'
                            to allocatingPort ::> 'CP 11'; 
                        ref :>> ownedPortAllocations =  ('79d9f8af-00e3-4b8f-a8da-cb940bb645ca'); 
                         
                    }  
                    ref :>> ownedFunctionalAllocation =  ('2f5f6884-289c-4d08-b057-0ade5c126910',
                    'd00598a5-2d5f-4397-bd10-9adb594c2181',
                    'c6650890-94b8-47a8-9704-b1325ee38f07',
                    'cdd8c38c-f71d-4f28-9a59-207642fd3831',
                    '242fa93a-e70f-4a46-960a-1c1f874c3d54',
                    'b6ea9ebb-5892-451e-98af-e32894877d6f',
                    '133ebbfa-7311-43c0-bf5e-798aa461b6ad',
                    'a9994fea-eb14-4353-858a-ae7ab7a7cf74',
                    '8a4ee225-5f52-4958-aeed-c96671a6e3bc',
                    'a14fba63-28ba-4b09-8144-5dfcaca7250f'); 
                     
                }  
                part 'Command &amp; Control' : PhysicalComponent { 
                    @CapellaID { eid = "43635c87-d1a6-469f-989a-f001e2aef69d"; sid = "43635c87-d1a6-469f-989a-f001e2aef69d"; } 
                    attribute :>> isAbstract = false; 
                    attribute :>> isActor = true; 
                    attribute :>> isHuman = true; 
                    attribute :>> kind = PhysicalComponentKind::UNSET; 
                    attribute :>> nature = PhysicalComponentNature::NODE; 
                    allocation '368519da-ee71-4c51-b175-342d315d33f5' : ComponentFunctionalAllocation
                        allocate function ::> 'Physical Functions'::'Root Physical Function'.'Monitor Execution'
                        to component ::> 'Structure'::'Command &amp; Control' { 
                        @CapellaID { eid = "368519da-ee71-4c51-b175-342d315d33f5"; sid = "368519da-ee71-4c51-b175-342d315d33f5"; } 
                         
                    } 
                    perform 'Physical Functions'::'Root Physical Function'.'Monitor Execution' ; 
                    allocation '3ef82e0f-82ae-490d-b529-e7333fbe2dea' : ComponentFunctionalAllocation
                        allocate function ::> 'Physical Functions'::'Root Physical Function'.'Ad Hoc Mission Update'
                        to component ::> 'Structure'::'Command &amp; Control' { 
                        @CapellaID { eid = "3ef82e0f-82ae-490d-b529-e7333fbe2dea"; sid = "3ef82e0f-82ae-490d-b529-e7333fbe2dea"; } 
                         
                    } 
                    perform 'Physical Functions'::'Root Physical Function'.'Ad Hoc Mission Update' ; 
                    ref :>> ownedFunctionalAllocation =  ('368519da-ee71-4c51-b175-342d315d33f5',
                    '3ef82e0f-82ae-490d-b529-e7333fbe2dea'); 
                     
                }  
                part 'Persons In Need' : PhysicalComponent { 
                    @CapellaID { eid = "f591b249-2f63-46bd-a440-b079c1b05b00"; sid = "f591b249-2f63-46bd-a440-b079c1b05b00"; } 
                    attribute :>> isAbstract = false; 
                    attribute :>> isActor = true; 
                    attribute :>> isHuman = true; 
                    attribute :>> kind = PhysicalComponentKind::UNSET; 
                    attribute :>> nature = PhysicalComponentNature::NODE; 
                    allocation '8fa7212b-fbc4-4ce9-89c9-b9031d2e3210' : ComponentFunctionalAllocation
                        allocate function ::> 'Physical Functions'::'Root Physical Function'.'Persons Supported'
                        to component ::> 'Structure'::'Persons In Need' { 
                        @CapellaID { eid = "8fa7212b-fbc4-4ce9-89c9-b9031d2e3210"; sid = "8fa7212b-fbc4-4ce9-89c9-b9031d2e3210"; } 
                         
                    } 
                    perform 'Physical Functions'::'Root Physical Function'.'Persons Supported' ; 
                    allocation '814508fa-f60e-4b32-bb35-ad92a9710704' : ComponentFunctionalAllocation
                        allocate function ::> 'Physical Functions'::'Root Physical Function'.'Persons Scanned'
                        to component ::> 'Structure'::'Persons In Need' { 
                        @CapellaID { eid = "814508fa-f60e-4b32-bb35-ad92a9710704"; sid = "814508fa-f60e-4b32-bb35-ad92a9710704"; } 
                         
                    } 
                    perform 'Physical Functions'::'Root Physical Function'.'Persons Scanned' ; 
                    port 'PP 1' : PhysicalPort { 
                        @CapellaID { eid = "4a042760-8e25-4d7b-b179-68d21adf2df3"; sid = "4a042760-8e25-4d7b-b179-68d21adf2df3"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    port 'CP 2' : ComponentPort { 
                        @CapellaID { eid = "e1c2a0ef-5675-4f10-8951-cdae80723c42"; sid = "e1c2a0ef-5675-4f10-8951-cdae80723c42"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                        ref allocation 'c994de9e-7481-42f6-881b-a34f4df87a7c' : PortAllocation
                            allocate allocatedPort ::> 'Physical Functions'::'Root Physical Function'.'Persons Scanned'.'FOP 1'
                            to allocatingPort ::> 'CP 2'; 
                        ref :>> ownedPortAllocations =  ('c994de9e-7481-42f6-881b-a34f4df87a7c'); 
                         
                    }  
                    ref :>> ownedFunctionalAllocation =  ('8fa7212b-fbc4-4ce9-89c9-b9031d2e3210',
                    '814508fa-f60e-4b32-bb35-ad92a9710704'); 
                     
                }  
                part 'Onsite Personnel' : PhysicalComponent { 
                    @CapellaID { eid = "db21db2f-00e3-4b87-b317-187d1e31fbc3"; sid = "db21db2f-00e3-4b87-b317-187d1e31fbc3"; } 
                    attribute :>> isAbstract = false; 
                    attribute :>> isActor = true; 
                    attribute :>> isHuman = true; 
                    attribute :>> kind = PhysicalComponentKind::UNSET; 
                    attribute :>> nature = PhysicalComponentNature::NODE; 
                    allocation '49553ae0-c056-4131-8d4c-1603f878b0ed' : ComponentFunctionalAllocation
                        allocate function ::> 'Physical Functions'::'Root Physical Function'.'Site Support'
                        to component ::> 'Structure'::'Onsite Personnel' { 
                        @CapellaID { eid = "49553ae0-c056-4131-8d4c-1603f878b0ed"; sid = "49553ae0-c056-4131-8d4c-1603f878b0ed"; } 
                         
                    } 
                    perform 'Physical Functions'::'Root Physical Function'.'Site Support' ; 
                    allocation '75694606-b17a-46da-bdc2-09fc4649adae' : ComponentFunctionalAllocation
                        allocate function ::> 'Physical Functions'::'Root Physical Function'.'Define Overflight Recon Mission'
                        to component ::> 'Structure'::'Onsite Personnel' { 
                        @CapellaID { eid = "75694606-b17a-46da-bdc2-09fc4649adae"; sid = "75694606-b17a-46da-bdc2-09fc4649adae"; } 
                         
                    } 
                    perform 'Physical Functions'::'Root Physical Function'.'Define Overflight Recon Mission' ; 
                    port 'PP 1' : PhysicalPort { 
                        @CapellaID { eid = "d80dcea1-1978-4f8c-90a7-ab13905cc1fe"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    port 'CP 2' : ComponentPort { 
                        @CapellaID { eid = "25b858b7-f44f-4b02-a3bd-7ff979fa3902"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                        ref allocation '3bb8239a-6d4a-43fa-97cf-5fee226ff2e2' : PortAllocation
                            allocate allocatedPort ::> 'Physical Functions'::'Root Physical Function'.'Define Overflight Recon Mission'.'outMIssion'
                            to allocatingPort ::> 'CP 2'; 
                        ref allocation '3d246b69-e3b9-4af8-a559-4a2f19c12ebc' : PortAllocation
                            allocate allocatedPort ::> 'Physical Functions'::'Root Physical Function'.'Site Support'.'FIP 1'
                            to allocatingPort ::> 'CP 2'; 
                        ref :>> ownedPortAllocations =  ('3bb8239a-6d4a-43fa-97cf-5fee226ff2e2',
                        '3d246b69-e3b9-4af8-a559-4a2f19c12ebc'); 
                         
                    }  
                    ref :>> ownedFunctionalAllocation =  ('49553ae0-c056-4131-8d4c-1603f878b0ed',
                    '75694606-b17a-46da-bdc2-09fc4649adae'); 
                     
                }  
                part 'Distressed Location' : PhysicalComponent { 
                    @CapellaID { eid = "4a01d25d-4fef-4889-9700-d1654fc33333"; sid = "1c559c12-07c5-4040-8b4d-7d18b261bbe8"; } 
                    attribute :>> isAbstract = false; 
                    attribute :>> isActor = true; 
                    attribute :>> isHuman = true; 
                    attribute :>> kind = PhysicalComponentKind::UNSET; 
                    attribute :>> nature = PhysicalComponentNature::NODE; 
                    allocation 'af576a3c-771e-4118-aeaf-37dbe59fec94' : ComponentFunctionalAllocation
                        allocate function ::> 'Physical Functions'::'Root Physical Function'.'Natural Disaster '
                        to component ::> 'Structure'::'Distressed Location' { 
                        @CapellaID { eid = "af576a3c-771e-4118-aeaf-37dbe59fec94"; sid = "af576a3c-771e-4118-aeaf-37dbe59fec94"; } 
                         
                    } 
                    perform 'Physical Functions'::'Root Physical Function'.'Natural Disaster ' ; 
                    port 'PP 1' : PhysicalPort { 
                        @CapellaID { eid = "fdecf090-8f3e-4d14-8960-ab760ccda428"; sid = "fdecf090-8f3e-4d14-8960-ab760ccda428"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    port 'CP 2' : ComponentPort { 
                        @CapellaID { eid = "d7952bb1-c8c1-498c-8a03-f7dc92f837b4"; sid = "d7952bb1-c8c1-498c-8a03-f7dc92f837b4"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                        ref allocation '1fff3118-2891-43c5-a20b-3a63dc35fa94' : PortAllocation
                            allocate allocatedPort ::> 'Physical Functions'::'Root Physical Function'.'Natural Disaster '.'outImage'
                            to allocatingPort ::> 'CP 2'; 
                        ref allocation '0f3ff760-9ee2-4432-ba2e-ac7915c52899' : PortAllocation
                            allocate allocatedPort ::> 'Physical Functions'::'Root Physical Function'.'Natural Disaster '.'outAudio Visual'
                            to allocatingPort ::> 'CP 2'; 
                        ref :>> ownedPortAllocations =  ('1fff3118-2891-43c5-a20b-3a63dc35fa94',
                        '0f3ff760-9ee2-4432-ba2e-ac7915c52899'); 
                         
                    }  
                    ref :>> ownedFunctionalAllocation =  ('af576a3c-771e-4118-aeaf-37dbe59fec94'); 
                     
                }  
                part 'SatCom' : PhysicalComponent { 
                    @CapellaID { eid = "f32485ff-87a7-411d-96fd-5f0bf2c9e293"; sid = "165b2ee2-4969-4e12-93f1-d114b44feb72"; } 
                    attribute :>> isAbstract = false; 
                    attribute :>> isActor = true; 
                    attribute :>> isHuman = false; 
                    attribute :>> kind = PhysicalComponentKind::UNSET; 
                    attribute :>> nature = PhysicalComponentNature::NODE; 
                    port 'PP 4' : PhysicalPort { 
                        @CapellaID { eid = "08a1a377-2be8-4bfa-93ce-b4579167d910"; sid = "de6aa9f4-90b5-4639-aab0-7bdb05f45b47"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    port 'PP 2' : PhysicalPort { 
                        @CapellaID { eid = "c0955f93-95be-4223-a57e-b72134fac4d1"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    port 'PP 3' : PhysicalPort { 
                        @CapellaID { eid = "ab37d95c-b0d8-40a8-8691-6516a3ff22cf"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    port 'PP 5' : PhysicalPort { 
                        @CapellaID { eid = "9627f64d-6e37-4a54-aa05-8c7fd281c22d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                     
                }  
                part 'Central Command' : PhysicalComponent { 
                    @CapellaID { eid = "d0f89f45-276b-4f17-a9cc-fc237f72afd0"; sid = "bd5c7207-ad23-4446-82ab-af5801d62b5c"; } 
                    attribute :>> isAbstract = false; 
                    attribute :>> isActor = true; 
                    attribute :>> isHuman = true; 
                    attribute :>> kind = PhysicalComponentKind::UNSET; 
                    attribute :>> nature = PhysicalComponentNature::NODE; 
                    allocation 'd8f0a51e-7fc8-4ec2-b360-baa9c8c2c101' : ComponentFunctionalAllocation
                        allocate function ::> 'Physical Functions'::'Root Physical Function'.'Collect Information  Distressed Location '
                        to component ::> 'Structure'::'Central Command' { 
                        @CapellaID { eid = "d8f0a51e-7fc8-4ec2-b360-baa9c8c2c101"; sid = "d8f0a51e-7fc8-4ec2-b360-baa9c8c2c101"; } 
                         
                    } 
                    perform 'Physical Functions'::'Root Physical Function'.'Collect Information  Distressed Location ' ; 
                    port 'PP 1' : PhysicalPort { 
                        @CapellaID { eid = "1d735255-5317-4542-9fec-f1ffda1395a8"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                         
                    }  
                    port 'D-CC' : ComponentPort { 
                        @CapellaID { eid = "92581fd4-3725-4b7d-a069-b70e6203f556"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                        ref allocation '9cff8c23-1bd8-4d66-996e-1d498ae1fa7b' : PortAllocation
                            allocate allocatedPort ::> 'Physical Functions'::'Root Physical Function'.'Collect Information  Distressed Location '.'inRecon Overflight Data'
                            to allocatingPort ::> 'D-CC'; 
                        ref :>> ownedPortAllocations =  ('9cff8c23-1bd8-4d66-996e-1d498ae1fa7b'); 
                         
                    }  
                    ref :>> ownedFunctionalAllocation =  ('d8f0a51e-7fc8-4ec2-b360-baa9c8c2c101'); 
                     
                }  
                part 'On SIte Personnel' : PhysicalComponent { 
                    @CapellaID { eid = "cd8cec44-8ca6-461e-968d-3f639a242d2a"; sid = "82d50bc9-3592-4814-bb13-02213f5352d2"; } 
                    attribute :>> isAbstract = false; 
                    attribute :>> isActor = true; 
                    attribute :>> isHuman = true; 
                    attribute :>> kind = PhysicalComponentKind::UNSET; 
                    attribute :>> nature = PhysicalComponentNature::NODE; 
                     
                }  
                part 'Runway' : PhysicalComponent { 
                    @CapellaID { eid = "3ee017fc-547b-4032-bcd3-d95afc5fdecc"; sid = "3ee017fc-547b-4032-bcd3-d95afc5fdecc"; } 
                    attribute :>> isAbstract = false; 
                    attribute :>> isActor = true; 
                    attribute :>> isHuman = false; 
                    attribute :>> kind = PhysicalComponentKind::UNSET; 
                    attribute :>> nature = PhysicalComponentNature::NODE; 
                    allocation 'cfe2b235-ae1d-4154-bacd-061bce9af9d8' : ComponentFunctionalAllocation
                        allocate function ::> 'Physical Functions'::'Root Physical Function'.'Provide Ground  Force'
                        to component ::> 'Structure'::'Runway' { 
                        @CapellaID { eid = "cfe2b235-ae1d-4154-bacd-061bce9af9d8"; } 
                         
                    } 
                    perform 'Physical Functions'::'Root Physical Function'.'Provide Ground  Force' ; 
                    allocation '4190b582-9a0e-4c48-9484-3dbefc8bac43' : ComponentFunctionalAllocation
                        allocate function ::> 'Physical Functions'::'Root Physical Function'.'Support LG'.'Gather 6'
                        to component ::> 'Structure'::'Runway' { 
                        @CapellaID { eid = "4190b582-9a0e-4c48-9484-3dbefc8bac43"; sid = "4190b582-9a0e-4c48-9484-3dbefc8bac43"; } 
                         
                    } 
                    perform 'Physical Functions'::'Root Physical Function'.'Support LG'.'Gather 6' ; 
                    allocation 'ee7c9dc0-99b7-4226-8562-f999a99fda24' : ComponentFunctionalAllocation
                        allocate function ::> 'Physical Functions'::'Root Physical Function'.'Provide Friction'
                        to component ::> 'Structure'::'Runway' { 
                        @CapellaID { eid = "ee7c9dc0-99b7-4226-8562-f999a99fda24"; sid = "ee7c9dc0-99b7-4226-8562-f999a99fda24"; } 
                         
                    } 
                    perform 'Physical Functions'::'Root Physical Function'.'Provide Friction' ; 
                    port 'PP 1' : PhysicalPort { 
                        @CapellaID { eid = "5d8782bf-7794-4545-b3a8-a1c020feea86"; sid = "5d8782bf-7794-4545-b3a8-a1c020feea86"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                        ref allocation 'a78e6f17-6644-43e3-bc8a-dcee5bf7aa93' : ComponentPortAllocation
                            allocate allocatedPort ::> 'PP 1'
                            to allocatingPort ::> 'Nose Landing Gear Library'::'Nose Landing Gear'::'Physical Architecture'::'Structure'::'Runway'.'CP 2' { 
                            @CapellaID { eid = "a78e6f17-6644-43e3-bc8a-dcee5bf7aa93"; } 
                             
                        }  
                         
                        ref :>> ownedComponentPortAllocations =  ('a78e6f17-6644-43e3-bc8a-dcee5bf7aa93'); 
                    }  
                    port 'CP 2' : ComponentPort { 
                        @CapellaID { eid = "91435aa7-b8fb-49c7-96f2-e1a77845ff65"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                        ref allocation 'df872646-24d2-41b4-883d-72e793443956' : PortAllocation
                            allocate allocatedPort ::> 'Physical Functions'::'Root Physical Function'.'Provide Ground  Force'.'FIP 4'
                            to allocatingPort ::> 'CP 2'; 
                        ref allocation 'd2580918-558b-4859-a814-40a2c2f0c9e5' : PortAllocation
                            allocate allocatedPort ::> 'Physical Functions'::'Root Physical Function'.'Provide Friction'.'FIP 5'
                            to allocatingPort ::> 'CP 2'; 
                        ref :>> ownedPortAllocations =  ('df872646-24d2-41b4-883d-72e793443956',
                        'd2580918-558b-4859-a814-40a2c2f0c9e5'); 
                         
                    }  
                    ref :>> ownedFunctionalAllocation =  ('cfe2b235-ae1d-4154-bacd-061bce9af9d8',
                    '4190b582-9a0e-4c48-9484-3dbefc8bac43',
                    'ee7c9dc0-99b7-4226-8562-f999a99fda24'); 
                     
                }  
                part 'Environment' : PhysicalComponent { 
                    @CapellaID { eid = "cc96b2a7-ecb5-48b8-ad58-fa4d25e0e690"; sid = "cc96b2a7-ecb5-48b8-ad58-fa4d25e0e690"; } 
                    attribute :>> isAbstract = false; 
                    attribute :>> isActor = true; 
                    attribute :>> isHuman = false; 
                    attribute :>> kind = PhysicalComponentKind::UNSET; 
                    attribute :>> nature = PhysicalComponentNature::NODE; 
                    allocation '8313b2d3-1a14-41a0-a018-cb3588317429' : ComponentFunctionalAllocation
                        allocate function ::> 'Physical Functions'::'Root Physical Function'.'Support LG'.'Gather 5'
                        to component ::> 'Structure'::'Environment' { 
                        @CapellaID { eid = "8313b2d3-1a14-41a0-a018-cb3588317429"; sid = "8313b2d3-1a14-41a0-a018-cb3588317429"; } 
                         
                    } 
                    perform 'Physical Functions'::'Root Physical Function'.'Support LG'.'Gather 5' ; 
                    ref :>> ownedFunctionalAllocation =  ('8313b2d3-1a14-41a0-a018-cb3588317429'); 
                     
                }  
                interface '1c7b637b-8400-4849-a9c1-f764e465a5e2' : ComponentExchange 
                    connect source ::> 'Physical System'.'Behavior Parent'.'ComLink'.'CP 1'
                    to  target ::> 'Central Command'.'D-CC' { 
                    @CapellaID { eid = "1c7b637b-8400-4849-a9c1-f764e465a5e2"; } 
                    attribute :>> kind = ComponentExchangeKind::FLOW; 
                    attribute :>> interfaceName = "COM-CC"; 
                    attribute :>> isOriented = false; 
                    allocation 'b8efd36e-7a15-489b-b8af-9f26ae3fb267' : ComponentExchangeFunctionalExchangeAllocation
                        allocate functionalExchange ::> 'Physical Functions'::'Root Physical Function'.'71ada17d-39af-44a8-ab4d-4a1e92c6231e'
                        to componentExchange ::> 'Structure'::'1c7b637b-8400-4849-a9c1-f764e465a5e2' { 
                        @CapellaID { eid = "b8efd36e-7a15-489b-b8af-9f26ae3fb267"; } 
                         
                    }  
                     
                    ref :>> ownedComponentExchangeFunctionalExchangeAllocations =  ('b8efd36e-7a15-489b-b8af-9f26ae3fb267'); 
                }  
                interface 'ca672d75-449b-4671-af67-238c6c5375f8' : ComponentExchange 
                    connect source ::> 'Operator/Pilot'.'CP 4'
                    to  target ::> 'Physical System'.'Behavior Parent'.'ComLink'.'CP 2' { 
                    @CapellaID { eid = "ca672d75-449b-4671-af67-238c6c5375f8"; } 
                    attribute :>> kind = ComponentExchangeKind::FLOW; 
                    attribute :>> interfaceName = "OP-Com"; 
                    attribute :>> isOriented = false; 
                    allocation '83b2a03d-fa03-46c4-9b46-5fc62cc49fcb' : ComponentExchangeFunctionalExchangeAllocation
                        allocate functionalExchange ::> 'Physical Functions'::'Root Physical Function'.'ff1adf05-fc1b-49b2-b2c8-df6a14d56eaf'
                        to componentExchange ::> 'Structure'::'ca672d75-449b-4671-af67-238c6c5375f8' { 
                        @CapellaID { eid = "83b2a03d-fa03-46c4-9b46-5fc62cc49fcb"; } 
                         
                    }  
                     
                    ref :>> ownedComponentExchangeFunctionalExchangeAllocations =  ('83b2a03d-fa03-46c4-9b46-5fc62cc49fcb'); 
                }  
                interface '6a3cd169-02c3-4c0a-8618-6093e99f8287' : ComponentExchange 
                    connect source ::> 'Operator/Pilot'.'CP 5'
                    to  target ::> 'Onsite Personnel'.'CP 2' { 
                    @CapellaID { eid = "6a3cd169-02c3-4c0a-8618-6093e99f8287"; } 
                    attribute :>> kind = ComponentExchangeKind::FLOW; 
                    attribute :>> interfaceName = "Op OP"; 
                    attribute :>> isOriented = false; 
                    allocation '98f617bd-7f6f-4841-99f5-06e68f5eee02' : ComponentExchangeFunctionalExchangeAllocation
                        allocate functionalExchange ::> 'Physical Functions'::'Root Physical Function'.'30c4fd48-fd98-416e-9086-feb98586279d'
                        to componentExchange ::> 'Structure'::'6a3cd169-02c3-4c0a-8618-6093e99f8287' { 
                        @CapellaID { eid = "98f617bd-7f6f-4841-99f5-06e68f5eee02"; } 
                         
                    }  
                    allocation '1d29997a-bcab-4c8f-aa67-f2d12342028a' : ComponentExchangeFunctionalExchangeAllocation
                        allocate functionalExchange ::> 'Physical Functions'::'Root Physical Function'.'4d82d33b-ac98-4319-bf5e-f8e2cab8e33d'
                        to componentExchange ::> 'Structure'::'6a3cd169-02c3-4c0a-8618-6093e99f8287' { 
                        @CapellaID { eid = "1d29997a-bcab-4c8f-aa67-f2d12342028a"; } 
                         
                    }  
                     
                    ref :>> ownedComponentExchangeFunctionalExchangeAllocations =  ('98f617bd-7f6f-4841-99f5-06e68f5eee02',
                    '1d29997a-bcab-4c8f-aa67-f2d12342028a'); 
                }  
                interface '14eaeda1-d17f-4aac-85a9-ec1483b2062e' : ComponentExchange 
                    connect source ::> 'Distressed Location'.'CP 2'
                    to  target ::> 'Physical System'.'Behavior Parent'.'Fuel and Power System'.'FLIR'.'CP 2' { 
                    @CapellaID { eid = "14eaeda1-d17f-4aac-85a9-ec1483b2062e"; sid = "14eaeda1-d17f-4aac-85a9-ec1483b2062e"; } 
                    attribute :>> kind = ComponentExchangeKind::FLOW; 
                    attribute :>> interfaceName = "DL-D"; 
                    attribute :>> isOriented = false; 
                    allocation 'c1f4c5a0-09b4-47c4-a034-0f3925a8df08' : ComponentExchangeFunctionalExchangeAllocation
                        allocate functionalExchange ::> 'Physical Functions'::'Root Physical Function'.'dab62d0a-f03a-4dc7-b11d-189881291644'
                        to componentExchange ::> 'Structure'::'14eaeda1-d17f-4aac-85a9-ec1483b2062e' { 
                        @CapellaID { eid = "c1f4c5a0-09b4-47c4-a034-0f3925a8df08"; sid = "c1f4c5a0-09b4-47c4-a034-0f3925a8df08"; } 
                         
                    }  
                    allocation 'db4c71cc-695c-45fc-b281-0b43dafb528d' : ComponentExchangeFunctionalExchangeAllocation
                        allocate functionalExchange ::> 'Physical Functions'::'Root Physical Function'.'1e89b679-4ee5-4fd3-8e47-a955e14e88a1'
                        to componentExchange ::> 'Structure'::'14eaeda1-d17f-4aac-85a9-ec1483b2062e' { 
                        @CapellaID { eid = "db4c71cc-695c-45fc-b281-0b43dafb528d"; sid = "db4c71cc-695c-45fc-b281-0b43dafb528d"; } 
                         
                    }  
                     
                    ref :>> ownedComponentExchangeFunctionalExchangeAllocations =  ('c1f4c5a0-09b4-47c4-a034-0f3925a8df08',
                    'db4c71cc-695c-45fc-b281-0b43dafb528d'); 
                }  
                interface '503d7f33-509f-4d8a-91a1-27205f3f9b58' : ComponentExchange 
                    connect source ::> 'Persons In Need'.'CP 2'
                    to  target ::> 'Physical System'.'Behavior Parent'.'Fuel and Power System'.'FLIR'.'CP 3' { 
                    @CapellaID { eid = "503d7f33-509f-4d8a-91a1-27205f3f9b58"; sid = "503d7f33-509f-4d8a-91a1-27205f3f9b58"; } 
                    attribute :>> kind = ComponentExchangeKind::FLOW; 
                    attribute :>> interfaceName = "PN-D"; 
                    attribute :>> isOriented = false; 
                    allocation '612957cd-c39f-4fb1-862f-e1348c10a6bd' : ComponentExchangeFunctionalExchangeAllocation
                        allocate functionalExchange ::> 'Physical Functions'::'Root Physical Function'.'bddbcd0d-3df2-4bff-95b1-9b19a6cdb267'
                        to componentExchange ::> 'Structure'::'503d7f33-509f-4d8a-91a1-27205f3f9b58' { 
                        @CapellaID { eid = "612957cd-c39f-4fb1-862f-e1348c10a6bd"; sid = "612957cd-c39f-4fb1-862f-e1348c10a6bd"; } 
                         
                    }  
                     
                    ref :>> ownedComponentExchangeFunctionalExchangeAllocations =  ('612957cd-c39f-4fb1-862f-e1348c10a6bd'); 
                }  
                interface '23f9683f-b3a6-4754-969a-615fa0b04131' : ComponentExchange 
                    connect source ::> 'Physical System'.'Behavior Parent'.'Isolation Valve'.'CP 2'
                    to  target ::> 'Physical System'.'Behavior Parent'.'Fuel and Power System'.'Selector Valve'.'CP 1' { 
                    @CapellaID { eid = "23f9683f-b3a6-4754-969a-615fa0b04131"; } 
                    attribute :>> kind = ComponentExchangeKind::FLOW; 
                    attribute :>> interfaceName = "C 5"; 
                    attribute :>> isOriented = false; 
                    allocation '4ed6df2a-c64d-4cf9-9ce3-04bb8b801f8e' : ComponentExchangeFunctionalExchangeAllocation
                        allocate functionalExchange ::> 'Physical Functions'::'Root Physical Function'.'9fc76035-36cb-46e9-af40-9f319ce9dd9b'
                        to componentExchange ::> 'Structure'::'23f9683f-b3a6-4754-969a-615fa0b04131' { 
                        @CapellaID { eid = "4ed6df2a-c64d-4cf9-9ce3-04bb8b801f8e"; } 
                         
                    }  
                     
                    ref :>> ownedComponentExchangeFunctionalExchangeAllocations =  ('4ed6df2a-c64d-4cf9-9ce3-04bb8b801f8e'); 
                }  
                interface '8a5c1bef-7ea0-4185-b32d-7d2c7410e6a5' : ComponentExchange 
                    connect source ::> 'Physical System'.'Behavior Parent'.'Blue Hydraulic Pump'.'CP 2'
                    to  target ::> 'Physical System'.'Behavior Parent'.'Isolation Valve'.'CP 1' { 
                    @CapellaID { eid = "8a5c1bef-7ea0-4185-b32d-7d2c7410e6a5"; } 
                    attribute :>> kind = ComponentExchangeKind::FLOW; 
                    attribute :>> interfaceName = "C 3"; 
                    attribute :>> isOriented = false; 
                    allocation 'e22f0228-90cb-4466-885f-c8739dc4ff0c' : ComponentExchangeFunctionalExchangeAllocation
                        allocate functionalExchange ::> 'Physical Functions'::'Root Physical Function'.'77535c9e-26f9-48f9-a652-dccbb875f365'
                        to componentExchange ::> 'Structure'::'8a5c1bef-7ea0-4185-b32d-7d2c7410e6a5' { 
                        @CapellaID { eid = "e22f0228-90cb-4466-885f-c8739dc4ff0c"; } 
                         
                    }  
                     
                    ref :>> ownedComponentExchangeFunctionalExchangeAllocations =  ('e22f0228-90cb-4466-885f-c8739dc4ff0c'); 
                }  
                interface '15bec8f8-2719-410b-a03f-55f91d61de09' : ComponentExchange 
                    connect source ::> 'Physical System'.'Behavior Parent'.'Fuel and Power System'.'Green Hydaulic Pump'.'CP 2'
                    to  target ::> 'Physical System'.'Behavior Parent'.'Shutoff Valve'.'CP 1' { 
                    @CapellaID { eid = "15bec8f8-2719-410b-a03f-55f91d61de09"; } 
                    attribute :>> kind = ComponentExchangeKind::FLOW; 
                    attribute :>> interfaceName = "C 4"; 
                    attribute :>> isOriented = false; 
                     
                }  
                interface '5ffef5ad-7f7e-4c19-9665-347aebcd36f8' : ComponentExchange 
                    connect source ::> 'Physical System'.'Behavior Parent'.'Shutoff Valve'.'CP 2'
                    to  target ::> 'Physical System'.'Behavior Parent'.'Fuel and Power System'.'Selector Valve'.'CP 2' { 
                    @CapellaID { eid = "5ffef5ad-7f7e-4c19-9665-347aebcd36f8"; } 
                    attribute :>> kind = ComponentExchangeKind::FLOW; 
                    attribute :>> interfaceName = "C 6"; 
                    attribute :>> isOriented = false; 
                    allocation '85f9a1de-a3b4-44ea-b4b3-fd7939e64d3f' : ComponentExchangeFunctionalExchangeAllocation
                        allocate functionalExchange ::> 'Physical Functions'::'Root Physical Function'.'40cd96ef-accd-416b-8716-89d7c25477f3'
                        to componentExchange ::> 'Structure'::'5ffef5ad-7f7e-4c19-9665-347aebcd36f8' { 
                        @CapellaID { eid = "85f9a1de-a3b4-44ea-b4b3-fd7939e64d3f"; } 
                         
                    }  
                     
                    ref :>> ownedComponentExchangeFunctionalExchangeAllocations =  ('85f9a1de-a3b4-44ea-b4b3-fd7939e64d3f'); 
                }  
                interface 'b18ca686-4e24-4e40-8653-6ee2b76eb327' : ComponentExchange 
                    connect source ::> 'Physical System'.'Behavior Parent'.'Fuel and Power System'.'Selector Valve'.'CP 3'
                    to  target ::> 'Physical System'.'Behavior Parent'.'Fuel and Power System'.'Junction'.'CP 1' { 
                    @CapellaID { eid = "b18ca686-4e24-4e40-8653-6ee2b76eb327"; } 
                    attribute :>> kind = ComponentExchangeKind::FLOW; 
                    attribute :>> interfaceName = "C 7"; 
                    attribute :>> isOriented = false; 
                    allocation '3697add3-70e7-4731-86a9-c426114bb857' : ComponentExchangeFunctionalExchangeAllocation
                        allocate functionalExchange ::> 'Physical Functions'::'Root Physical Function'.'ae78d464-1d1a-4c52-85da-8e596ee0dd6b'
                        to componentExchange ::> 'Structure'::'b18ca686-4e24-4e40-8653-6ee2b76eb327' { 
                        @CapellaID { eid = "3697add3-70e7-4731-86a9-c426114bb857"; } 
                         
                    }  
                     
                    ref :>> ownedComponentExchangeFunctionalExchangeAllocations =  ('3697add3-70e7-4731-86a9-c426114bb857'); 
                }  
                interface 'c46f883c-7cfa-4196-a61f-d6805e25aafb' : ComponentExchange 
                    connect source ::> 'Operator/Pilot'.'CP 9'
                    to  target ::> 'Physical System'.'Behavior Parent'.'Extension Retraction Lever'.'CP 1' { 
                    @CapellaID { eid = "c46f883c-7cfa-4196-a61f-d6805e25aafb"; } 
                    attribute :>> kind = ComponentExchangeKind::FLOW; 
                    attribute :>> interfaceName = "C 11"; 
                    attribute :>> isOriented = false; 
                    allocation '2087b287-bf74-4a0e-9b67-63a21e83fa8c' : ComponentExchangeFunctionalExchangeAllocation
                        allocate functionalExchange ::> 'Physical Functions'::'Root Physical Function'.'01616769-4383-43bc-8c1d-2a6ead7c722f'
                        to componentExchange ::> 'Structure'::'c46f883c-7cfa-4196-a61f-d6805e25aafb' { 
                        @CapellaID { eid = "2087b287-bf74-4a0e-9b67-63a21e83fa8c"; } 
                         
                    }  
                     
                    ref :>> ownedComponentExchangeFunctionalExchangeAllocations =  ('2087b287-bf74-4a0e-9b67-63a21e83fa8c'); 
                }  
                interface 'c89e34fa-5729-4525-a278-ad54dd485377' : ComponentExchange 
                    connect source ::> 'Operator/Pilot'.'CP 10'
                    to  target ::> 'Physical System'.'Behavior Parent'.'Fuel and Power System'.'Dump Control'.'CP 1' { 
                    @CapellaID { eid = "c89e34fa-5729-4525-a278-ad54dd485377"; } 
                    attribute :>> kind = ComponentExchangeKind::FLOW; 
                    attribute :>> interfaceName = "C 12"; 
                    attribute :>> isOriented = false; 
                    allocation '2264bb14-b02d-415f-82e8-cd7216ffd3fe' : ComponentExchangeFunctionalExchangeAllocation
                        allocate functionalExchange ::> 'Physical Functions'::'Root Physical Function'.'49abf19d-43b3-49a7-a4c6-7cfe88216935'
                        to componentExchange ::> 'Structure'::'c89e34fa-5729-4525-a278-ad54dd485377' { 
                        @CapellaID { eid = "2264bb14-b02d-415f-82e8-cd7216ffd3fe"; } 
                         
                    }  
                     
                    ref :>> ownedComponentExchangeFunctionalExchangeAllocations =  ('2264bb14-b02d-415f-82e8-cd7216ffd3fe'); 
                }  
                interface '1db3548f-b512-4cd5-b154-af3dfe89f171' : ComponentExchange 
                    connect source ::> 'Operator/Pilot'.'CP 11'
                    to  target ::> 'Physical System'.'Behavior Parent'.'Fuel and Power System'.'Dump Control'.'CP 2' { 
                    @CapellaID { eid = "1db3548f-b512-4cd5-b154-af3dfe89f171"; } 
                    attribute :>> kind = ComponentExchangeKind::FLOW; 
                    attribute :>> interfaceName = "C 13"; 
                    attribute :>> isOriented = false; 
                    allocation 'e5265336-1f4a-45eb-bb13-2179691e6117' : ComponentExchangeFunctionalExchangeAllocation
                        allocate functionalExchange ::> 'Physical Functions'::'Root Physical Function'.'78c4630d-fda8-439f-abcf-3773df772c00'
                        to componentExchange ::> 'Structure'::'1db3548f-b512-4cd5-b154-af3dfe89f171' { 
                        @CapellaID { eid = "e5265336-1f4a-45eb-bb13-2179691e6117"; } 
                         
                    }  
                     
                    ref :>> ownedComponentExchangeFunctionalExchangeAllocations =  ('e5265336-1f4a-45eb-bb13-2179691e6117'); 
                }  
                interface 'd687cc15-9a49-494d-b5ec-16154f13c6f4' : ComponentExchange 
                    connect source ::> 'Physical System'.'Behavior Parent'.'NLG Wheel'.'CP 4'
                    to  target ::> 'Runway'.'CP 2' { 
                    @CapellaID { eid = "d687cc15-9a49-494d-b5ec-16154f13c6f4"; } 
                    attribute :>> kind = ComponentExchangeKind::FLOW; 
                    attribute :>> interfaceName = "NLG Wheel to Runway Interface"; 
                    attribute :>> isOriented = false; 
                    allocation '6a36356c-0029-4a1a-bc51-2b8a9f36ba3d' : ComponentExchangeFunctionalExchangeAllocation
                        allocate functionalExchange ::> 'Physical Functions'::'Root Physical Function'.'7cee4409-2d70-49cf-9ffa-b6541a64d7e4'
                        to componentExchange ::> 'Structure'::'d687cc15-9a49-494d-b5ec-16154f13c6f4' { 
                        @CapellaID { eid = "6a36356c-0029-4a1a-bc51-2b8a9f36ba3d"; } 
                         
                    }  
                    allocation 'e5be6fcb-aeaf-47e8-bf63-84267bde4eb9' : ComponentExchangeFunctionalExchangeAllocation
                        allocate functionalExchange ::> 'Physical Functions'::'Root Physical Function'.'14d27697-47bf-4616-9758-b1dd5dcf8edf'
                        to componentExchange ::> 'Structure'::'d687cc15-9a49-494d-b5ec-16154f13c6f4' { 
                        @CapellaID { eid = "e5be6fcb-aeaf-47e8-bf63-84267bde4eb9"; } 
                         
                    }  
                     
                    ref :>> ownedComponentExchangeFunctionalExchangeAllocations =  ('6a36356c-0029-4a1a-bc51-2b8a9f36ba3d',
                    'e5be6fcb-aeaf-47e8-bf63-84267bde4eb9'); 
                }  
            } 
            package 'Physical Functions' {
                @PackageMeta {
                    type = "PhysicalFunctionPkg";
                } 
                @CapellaID { eid = "c9885732-5d10-4841-9c97-f328696eb46a"; } 
                action 'Root Physical Function' : PhysicalFunction  { 
                    @CapellaID { eid = "ac1b0ba4-f7ff-421a-8dee-cdca14334c46"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> kind = FunctionKind::FUNCTION; 
                    attribute :>> isMaxInclusive = false; 
                    attribute :>> isMinInclusive = false; 
                    attribute :>> isOrdered = false; 
                    attribute :>> isUnique = false; 
                    action 'Mission Execution' : FunctionalChain  { 
                        @CapellaID { eid = "7d8e43a0-922f-4a23-9c4b-69aae1080b7e"; sid = "7d8e43a0-922f-4a23-9c4b-69aae1080b7e"; } 
                        attribute :>> kind = FunctionalChainKind::SIMPLE; 
                        connection '4df27504-422e-4331-9587-7ebeb64de1f3' : FunctionalChainInvolvementLink 
                            connect source ::> '695fa82b-5da7-4352-a356-01d25724760e'
                            to  target ::> 'c3f167a7-5b27-45d9-b7fd-f792153cec1f' {

                                ref :>> involved = '0dec75ca-92e1-492c-b25d-fa132c5454c2';

                            } 
                        connection 'bfc7099d-12e9-490c-9542-7d4938bb2193' : FunctionalChainInvolvementLink 
                            connect source ::> 'c3f167a7-5b27-45d9-b7fd-f792153cec1f'
                            to  target ::> '72fc7cab-21b7-41de-9303-f3040d9eecc0' {

                                ref :>> involved = '93290df8-fed9-49d1-beed-b9aaf7a44f24';

                            } 
                        connection '2d4460e3-8c6a-4546-b9b2-b6ec1432e255' : FunctionalChainInvolvementLink 
                            connect source ::> '799b218e-b8d1-4b53-8f04-fb3bebf8fb01'
                            to  target ::> '08f4d31c-5bd1-4ccf-9e0f-b3c239ed9e1e' {

                                ref :>> involved = 'a9c8c5d1-a0aa-4fa8-9841-84cf667fb6e7';

                            } 
                        connection '72de9564-4d08-46a8-ae23-a54579ad8901' : FunctionalChainInvolvementLink 
                            connect source ::> '5d6855d5-b4f9-4072-8127-c6e88690ef2e'
                            to  target ::> 'a73b76a8-0a12-4d15-ab76-a415e05dba24' {

                                ref :>> involved = '98a1d99f-7d1b-4bf7-8389-e9648c7ba5c0';

                            } 
                        connection '5dce7db1-002b-47eb-ae35-eb4585d91359' : FunctionalChainInvolvementLink 
                            connect source ::> 'a73b76a8-0a12-4d15-ab76-a415e05dba24'
                            to  target ::> 'a841dc30-dba3-43a1-8fb3-b64527a20577' {

                                ref :>> involved = '4eb9f09b-b4e7-49a1-a73a-3346c16bd1f9';

                            } 
                        ref action '695fa82b-5da7-4352-a356-01d25724760e' = 'Initiate Mission'; 
                        ref action '799b218e-b8d1-4b53-8f04-fb3bebf8fb01' = 'Perform Overflight Recon Mission'.'Perform Scan'; 
                        ref action 'a841dc30-dba3-43a1-8fb3-b64527a20577' = 'Interpreted Analysis Response'; 
                        ref action 'f98c7ba8-be7e-4592-87fe-0a29cd1b0e89' = 'Persons Scanned'; 
                        ref action 'c3f167a7-5b27-45d9-b7fd-f792153cec1f' = 'Scan'; 
                        ref action 'a73b76a8-0a12-4d15-ab76-a415e05dba24' = 'Interpret Analysis'; 
                        ref action '5d6855d5-b4f9-4072-8127-c6e88690ef2e' = 'Analysis'; 
                        ref action 'db3a7168-6f73-437e-9e1f-cbbe5fd6c788' = 'Support Response'; 
                        ref action '6d57806b-4ec8-4b11-8d51-f6da2c31b18b' = 'Perform Drone Recon'; 
                        connection 'df1b0544-29df-4faa-9948-69c31669fa79' : FunctionalChainInvolvementLink 
                            connect source ::> 'c3f167a7-5b27-45d9-b7fd-f792153cec1f'
                            to  target ::> '72fc7cab-21b7-41de-9303-f3040d9eecc0' {

                                ref :>> involved = '93290df8-fed9-49d1-beed-b9aaf7a44f24';

                            } 
                        connection 'ee7c2c42-8e3a-41ae-9b30-7976d4a3ac4c' : FunctionalChainInvolvementLink 
                            connect source ::> 'a841dc30-dba3-43a1-8fb3-b64527a20577'
                            to  target ::> 'db3a7168-6f73-437e-9e1f-cbbe5fd6c788' {

                                ref :>> involved = '4e29bbc1-ea33-40a6-a5a2-61e1dbf63ae6';

                            } 
                        connection 'dc00acec-28b3-45fe-9534-33e06e57c01e' : FunctionalChainInvolvementLink 
                            connect source ::> 'Perform Drone Recon'.'b293e937-c96a-4303-8078-76bab9608cc3'
                            to  target ::> 'fa048903-3e8b-4b38-9933-3880d5d2eb5d' {

                                ref :>> involved = '12340e91-350b-40c8-8074-7d3584ea3bea';

                            } 
                        ref action 'fa048903-3e8b-4b38-9933-3880d5d2eb5d' = 'Relay to Operator'; 
                        ref action '72fc7cab-21b7-41de-9303-f3040d9eecc0' = 'Gather 35'; 
                        connection '6da8a9f1-4391-44c3-abd4-72986cb974de' : FunctionalChainInvolvementLink 
                            connect source ::> '72fc7cab-21b7-41de-9303-f3040d9eecc0'
                            to  target ::> '799b218e-b8d1-4b53-8f04-fb3bebf8fb01' {

                                ref :>> involved = '15984110-47d2-40e5-adc6-049128b8eb66';

                            } 
                        connection '8957f74f-b6c1-4db0-93cf-b69a3a3d393d' : FunctionalChainInvolvementLink 
                            connect source ::> 'f98c7ba8-be7e-4592-87fe-0a29cd1b0e89'
                            to  target ::> 'Perform Drone Recon'.'4a645e98-b327-4140-9d19-bc73f9a98952' {

                                ref :>> involved = 'bddbcd0d-3df2-4bff-95b1-9b19a6cdb267';

                            } 
                        connection '53ea91be-9eb8-41ea-85cb-fd5b286476bd' : FunctionalChainInvolvementLink 
                            connect source ::> 'fa048903-3e8b-4b38-9933-3880d5d2eb5d'
                            to  target ::> 'db3a7168-6f73-437e-9e1f-cbbe5fd6c788' {

                                ref :>> involved = 'ff1adf05-fc1b-49b2-b2c8-df6a14d56eaf';

                            } 
                        ref action '08f4d31c-5bd1-4ccf-9e0f-b3c239ed9e1e' = 'Activate Scan'; 
                        connection '843e16b5-213c-4d72-8222-3e0984ef5ac3' : FunctionalChainInvolvementLink 
                            connect source ::> '08f4d31c-5bd1-4ccf-9e0f-b3c239ed9e1e'
                            to  target ::> 'Perform Drone Recon'.'4a645e98-b327-4140-9d19-bc73f9a98952' {

                                ref :>> involved = '24a38b00-19b1-48de-850e-4f435028df88';

                            } 
                        connection '0b09dbc8-f657-4181-ac85-93b4b6c6d5c4' : FunctionalChainInvolvementLink 
                            connect source ::> '08f4d31c-5bd1-4ccf-9e0f-b3c239ed9e1e'
                            to  target ::> 'Perform Drone Recon'.'bdfa8009-aeea-4471-ba6b-d8069deee6b1' {

                                ref :>> involved = '3636a890-f283-4557-8fbf-87c7fbd83013';

                            } 
                         
                    }  
                    action 'Support Response' : FunctionalChain  { 
                        @CapellaID { eid = "bf042d3c-db33-4019-92cd-6a5688f4d8de"; sid = "bf042d3c-db33-4019-92cd-6a5688f4d8de"; } 
                        attribute :>> kind = FunctionalChainKind::SIMPLE; 
                        ref action '3af48866-7406-490f-a78f-d286abaa408b' = 'Nose Landing Gear Library'::'Nose Landing Gear'::'Physical Architecture'::'Physical Functions'::'Root Physical Function'.'Support Response'; 
                        ref action 'ba0ebb8e-79d1-411d-a1aa-c1e501ac1849' = 'Site Support'; 
                        connection '85753413-ced4-4c88-b29c-bd550bc0194f' : FunctionalChainInvolvementLink 
                            connect source ::> '3af48866-7406-490f-a78f-d286abaa408b'
                            to  target ::> 'ba0ebb8e-79d1-411d-a1aa-c1e501ac1849' {

                                ref :>> involved = '4d82d33b-ac98-4319-bf5e-f8e2cab8e33d';

                            } 
                        ref action '1e0ccc85-c93c-495d-bc53-b7cb4e2ed1ca' = 'Persons Supported'; 
                        connection '114d7f44-5e59-42fd-bc38-89017e5c1f7f' : FunctionalChainInvolvementLink 
                            connect source ::> 'ba0ebb8e-79d1-411d-a1aa-c1e501ac1849'
                            to  target ::> '1e0ccc85-c93c-495d-bc53-b7cb4e2ed1ca' {

                                ref :>> involved = 'f072ef8d-3125-471c-829f-6f95ca80097e';

                            } 
                         
                    }  
                    action 'Mission Update' : FunctionalChain  { 
                        @CapellaID { eid = "59daa6ba-340d-422a-9f0b-7d5d73cb053b"; sid = "59daa6ba-340d-422a-9f0b-7d5d73cb053b"; } 
                        attribute :>> kind = FunctionalChainKind::SIMPLE; 
                        ref action 'fa145820-9c90-434f-b56a-7141da8b37f1' = 'Update SITREP'; 
                        ref action '155cd2a9-555c-44a9-b423-7ba940d43af8' = 'Provide C&amp;C SITREP'; 
                        connection '330e79ae-2680-488a-9470-fe09260ee8b1' : FunctionalChainInvolvementLink 
                            connect source ::> 'fa145820-9c90-434f-b56a-7141da8b37f1'
                            to  target ::> '155cd2a9-555c-44a9-b423-7ba940d43af8' {

                                ref :>> involved = '1dc07bf7-2f2a-408a-b55d-537a90f10368';

                            } 
                        ref action '2ab4df74-bd0c-466e-89ff-df12695582fc' = 'Interpret SITREP'; 
                        connection '4ad372f1-0872-421e-b36c-52a7867a165a' : FunctionalChainInvolvementLink 
                            connect source ::> 'fa145820-9c90-434f-b56a-7141da8b37f1'
                            to  target ::> '2ab4df74-bd0c-466e-89ff-df12695582fc' {

                                ref :>> involved = '84a01918-f6c0-4f3b-9697-4a42fd16534e';

                            } 
                        ref action 'a32830e7-a55a-42d4-b18a-f97464abf7f8' = 'Monitor Execution'; 
                        connection 'a510590b-b245-49d9-80ce-09a53e85a7f5' : FunctionalChainInvolvementLink 
                            connect source ::> '155cd2a9-555c-44a9-b423-7ba940d43af8'
                            to  target ::> 'a32830e7-a55a-42d4-b18a-f97464abf7f8' {

                                ref :>> involved = 'a16b1418-33f2-4af9-b77b-52af39f442f4';

                            } 
                        ref action '13d0aa7c-9428-4798-ac20-c5bbfcfb7dd0' = 'Ad Hoc Mission Update'; 
                        connection '6bb9b953-5894-4dab-b078-a5266bd22f36' : FunctionalChainInvolvementLink 
                            connect source ::> 'a32830e7-a55a-42d4-b18a-f97464abf7f8'
                            to  target ::> '13d0aa7c-9428-4798-ac20-c5bbfcfb7dd0' {

                                ref :>> involved = '92c595ae-1023-4c82-8220-7f2b2eb1bdd0';

                            } 
                        ref action 'fbd51db7-571c-4ad9-8e9d-6e7c36e71a47' = 'Ad Hoc Mission Execution Update'; 
                        connection 'bb729b6a-b046-4001-b070-b5d73f5abf4b' : FunctionalChainInvolvementLink 
                            connect source ::> '2ab4df74-bd0c-466e-89ff-df12695582fc'
                            to  target ::> 'fbd51db7-571c-4ad9-8e9d-6e7c36e71a47' {

                                ref :>> involved = '795262b4-e5cc-4f7e-b06e-7108bfe01fd4';

                            } 
                        ref action '9d0c4f82-c033-44cd-b4f8-73bb00d351b4' = 'Ad Hoc Mission Update Response'; 
                        connection 'e1d3558d-4a91-41d1-8b70-bf271c057116' : FunctionalChainInvolvementLink 
                            connect source ::> 'fbd51db7-571c-4ad9-8e9d-6e7c36e71a47'
                            to  target ::> '9d0c4f82-c033-44cd-b4f8-73bb00d351b4' {

                                ref :>> involved = '141959c3-cb9c-4778-88fa-dcf48fc230b3';

                            } 
                        connection '7308713a-41b6-401c-8f71-d8fe780e9c79' : FunctionalChainInvolvementLink 
                            connect source ::> '13d0aa7c-9428-4798-ac20-c5bbfcfb7dd0'
                            to  target ::> '2ab4df74-bd0c-466e-89ff-df12695582fc' {

                                ref :>> involved = 'ab243386-52d7-459d-9707-6a18abbb9b83';

                            } 
                        ref action '7dafc651-7765-4843-b20a-6aa3ce2c0a8e' = 'Action Report'; 
                        connection 'd970f850-a6be-445f-ba80-e5cdb1179217' : FunctionalChainInvolvementLink 
                            connect source ::> '7dafc651-7765-4843-b20a-6aa3ce2c0a8e'
                            to  target ::> 'fa145820-9c90-434f-b56a-7141da8b37f1' {

                                ref :>> involved = '3f900ac2-d70a-4712-b1f3-2579db25b4e8';

                            } 
                        ref action 'ef409702-e01f-40fc-87b0-55581945357d' = 'Site Support'; 
                        connection '380d0cfc-1be1-41e3-b2fb-2ece88648542' : FunctionalChainInvolvementLink 
                            connect source ::> 'ef409702-e01f-40fc-87b0-55581945357d'
                            to  target ::> '7dafc651-7765-4843-b20a-6aa3ce2c0a8e' {

                                ref :>> involved = 'ad3df3f1-f31f-4b45-9438-4f06a86e4152';

                            } 
                         
                    }  
                    action 'Perform Drone Recon' : FunctionalChain  { 
                        @CapellaID { eid = "b2010a8a-33b7-4895-a78b-51ee159071a4"; sid = "b2010a8a-33b7-4895-a78b-51ee159071a4"; } 
                        attribute :>> kind = FunctionalChainKind::SIMPLE; 
                        ref action 'b293e937-c96a-4303-8078-76bab9608cc3' = 'Locate Trapped People'; 
                        connection 'b1c007a9-5c89-4b9f-bc0c-e925181cf2e7' : FunctionalChainInvolvementLink 
                            connect source ::> 'b293e937-c96a-4303-8078-76bab9608cc3'
                            to  target ::> '326065aa-d631-41b3-ab37-c4e332e4cfdb' {

                                ref :>> involved = '85621e3d-1a84-45af-9235-c37b1a7aa9bd';

                            } 
                        ref action 'bdfa8009-aeea-4471-ba6b-d8069deee6b1' = 'Capture Photos'; 
                        connection '937a76b3-0271-45a4-bc5e-b66559267295' : FunctionalChainInvolvementLink 
                            connect source ::> 'bdfa8009-aeea-4471-ba6b-d8069deee6b1'
                            to  target ::> '92d1f37b-9b2c-4b93-8e67-70f6b804ddaa' {

                                ref :>> involved = '844fdd8e-cc79-44c9-abe8-9d977e6bf76d';

                            } 
                        ref action '326065aa-d631-41b3-ab37-c4e332e4cfdb' = 'Relay Overflight Data from Drone Mission'; 
                        ref action '4a645e98-b327-4140-9d19-bc73f9a98952' = 'Capture Video'; 
                        connection '5b49fa38-a8aa-44c1-9875-7e939f3c0988' : FunctionalChainInvolvementLink 
                            connect source ::> '4a645e98-b327-4140-9d19-bc73f9a98952'
                            to  target ::> '92d1f37b-9b2c-4b93-8e67-70f6b804ddaa' {

                                ref :>> involved = 'b141216c-80c6-4f2e-b648-67772db4f2b3';

                            } 
                        ref action 'b7a3de98-c824-49a6-b484-e6021cc707e3' = 'Natural Disaster '; 
                        connection '9f4498b0-4da2-45b1-a030-a8e4243fbc80' : FunctionalChainInvolvementLink 
                            connect source ::> 'b7a3de98-c824-49a6-b484-e6021cc707e3'
                            to  target ::> '4a645e98-b327-4140-9d19-bc73f9a98952' {

                                ref :>> involved = '1e89b679-4ee5-4fd3-8e47-a955e14e88a1';

                            } 
                        connection 'b9b21ade-aca6-4c46-b06b-646c7881f966' : FunctionalChainInvolvementLink 
                            connect source ::> 'b7a3de98-c824-49a6-b484-e6021cc707e3'
                            to  target ::> 'bdfa8009-aeea-4471-ba6b-d8069deee6b1' {

                                ref :>> involved = 'dab62d0a-f03a-4dc7-b11d-189881291644';

                            } 
                        connection '7ef1c6a0-473e-4bd9-8e52-e0e7b89df348' : FunctionalChainInvolvementLink 
                            connect source ::> '92d1f37b-9b2c-4b93-8e67-70f6b804ddaa'
                            to  target ::> 'b293e937-c96a-4303-8078-76bab9608cc3' {

                                ref :>> involved = 'a60fd365-b419-40ea-b7ba-12a94748c12e';

                            } 
                        ref action '5a6dde3e-cdab-4a51-b15d-939bbea8d23e' = 'Collect Information  Distressed Location '; 
                        connection 'b234435d-bff3-467a-ba4f-aec3387602fc' : FunctionalChainInvolvementLink 
                            connect source ::> '326065aa-d631-41b3-ab37-c4e332e4cfdb'
                            to  target ::> '5a6dde3e-cdab-4a51-b15d-939bbea8d23e' {

                                ref :>> involved = '71ada17d-39af-44a8-ab4d-4a1e92c6231e';

                            } 
                        ref action '92d1f37b-9b2c-4b93-8e67-70f6b804ddaa' = 'Image Storage'; 
                        connection 'c4066553-0018-4cf3-8c67-4c6021732038' : FunctionalChainInvolvementLink 
                            connect source ::> '92d1f37b-9b2c-4b93-8e67-70f6b804ddaa'
                            to  target ::> '326065aa-d631-41b3-ab37-c4e332e4cfdb' {

                                ref :>> involved = '9a7c1e82-e3d2-4539-a01b-7569bbb0939f';

                            } 
                         
                    }  
                    action 'Groundforce on Airframe' : FunctionalChain  { 
                        @CapellaID { eid = "8b856a84-8f76-44d1-88de-cac2fd5d04c9"; } 
                        attribute :>> kind = FunctionalChainKind::SIMPLE; 
                        ref action '51d9fefd-ea36-4ae5-be81-1f76c6b93f3b' = 'Provide Ground  Force'; 
                        connection 'bf267c5e-5145-47a9-ab80-25c790cfc6a0' : FunctionalChainInvolvementLink 
                            connect source ::> 'ebd9f15c-e31d-4541-83c4-902cad7ac779'
                            to  target ::> '15cf3fe4-f9b7-4195-8639-ac34759f353d' {

                                ref :>> involved = '16a8d621-e576-4365-bbb3-e65bea6bff08';

                            } 
                        ref action 'ee65690c-8bd4-4233-8545-e0dc981095fb' = 'Transmit NLG Forces'; 
                        ref action '1d9f4e05-6083-499b-a1ba-933aea7db675' = 'Transmit LG Force'; 
                        ref action 'b7814941-32c2-461e-887d-e84980fa4ad8' = 'Transmit Ground Force'; 
                        ref action 'f4d1651f-43d8-4005-afb7-b517b7d78019' = 'Tranmit'; 
                        connection '97491061-48ad-483c-b440-012f8ed0fbee' : FunctionalChainInvolvementLink 
                            connect source ::> 'b7814941-32c2-461e-887d-e84980fa4ad8'
                            to  target ::> '1d9f4e05-6083-499b-a1ba-933aea7db675' {

                                ref :>> involved = '5441eb90-cfa9-4f55-96de-54e7625462c1';

                            } 
                        connection '1efa2fec-a2fe-4d41-b66b-621fabf1236c' : FunctionalChainInvolvementLink 
                            connect source ::> 'f4d1651f-43d8-4005-afb7-b517b7d78019'
                            to  target ::> '1d9f4e05-6083-499b-a1ba-933aea7db675' {

                                ref :>> involved = '73b4b16a-bf09-4603-81c1-9748d4dae983';

                            } 
                        connection '1db7f239-74f7-4474-a934-02cdb83059e7' : FunctionalChainInvolvementLink 
                            connect source ::> '1d9f4e05-6083-499b-a1ba-933aea7db675'
                            to  target ::> 'ceb3f960-bf6e-4373-9468-d746fc07f82c' {

                                ref :>> involved = '3dd2c494-03e4-4511-8229-90df30f2fb6a';

                            } 
                        ref action 'ceb3f960-bf6e-4373-9468-d746fc07f82c' = 'Support '; 
                        ref action '15cf3fe4-f9b7-4195-8639-ac34759f353d' = 'Transmit NLG Forces'.'Dampen Spring'; 
                        ref action 'ecb5ec2a-bb24-41d1-ac20-74d4053ad40c' = 'Transmit NLG Forces'.'Transmit NLG Structural Post'; 
                        ref action 'ebd9f15c-e31d-4541-83c4-902cad7ac779' = 'Measure'.'Actuate NLG'.'Apply Force Runway'; 
                         
                    }  
                    action 'WoW Sense' : FunctionalChain  { 
                        @CapellaID { eid = "5d4b7797-6b2f-4ba4-ba08-71d02a391f60"; } 
                        attribute :>> kind = FunctionalChainKind::SIMPLE; 
                        connection 'fe656e1f-e80c-4d4e-a145-29ba89e059c3' : FunctionalChainInvolvementLink 
                            connect source ::> '103752c2-2378-4b09-a6b9-1d9c3a3304b9'
                            to  target ::> 'aa8a9240-8b0e-422a-bf60-f68c68ad473a' {

                                ref :>> involved = '004b4ee4-f50b-47d8-8ab8-684a3165d440';

                            } 
                        ref action 'aa8a9240-8b0e-422a-bf60-f68c68ad473a' = 'Sense NLG State'; 
                        ref action '103752c2-2378-4b09-a6b9-1d9c3a3304b9' = 'Sense Weight on Wheels 2'; 
                        connection 'ccb0199c-2e37-41d9-8ba3-57baadda6650' : FunctionalChainInvolvementLink 
                            connect source ::> 'd934b800-4dcc-4715-9396-13b73bf53549'
                            to  target ::> 'aa8a9240-8b0e-422a-bf60-f68c68ad473a' {

                                ref :>> involved = '1d0ef78d-bb0c-4929-ace7-8d0818fef271';

                            } 
                        ref action 'd934b800-4dcc-4715-9396-13b73bf53549' = 'Sense Weight on Wheels'; 
                         
                    }  
                    action 'NLG Door Sense' : FunctionalChain  { 
                        @CapellaID { eid = "67f1655d-d0d8-41fe-bcce-83e2b9ce33b2"; } 
                        attribute :>> kind = FunctionalChainKind::SIMPLE; 
                        connection 'ed3b818c-d2fe-4f1e-a0a5-7204175800d7' : FunctionalChainInvolvementLink 
                            connect source ::> 'fa1309db-98a8-4357-84bc-d64c03c2771e'
                            to  target ::> '9657d1d8-412a-4a70-9465-00de82bf52de' {

                                ref :>> involved = 'e586d180-2195-4911-ae8a-04dcef046776';

                            } 
                        ref action '9657d1d8-412a-4a70-9465-00de82bf52de' = 'Sense NLG State'; 
                        ref action 'fa1309db-98a8-4357-84bc-d64c03c2771e' = 'Sense Hardware'.'Sense NLG Door Position'; 
                         
                    }  
                    action 'NLG Dwnlock Sense' : FunctionalChain  { 
                        @CapellaID { eid = "0d99900e-7918-4967-9e52-422e4fc91693"; } 
                        attribute :>> kind = FunctionalChainKind::SIMPLE; 
                        connection '4e57fca6-67bf-429e-a1a4-854d9f2c116b' : FunctionalChainInvolvementLink 
                            connect source ::> 'ecd3854f-763d-455b-950e-6252d312040e'
                            to  target ::> '0b47e37a-cba3-4f2f-a450-d84fbd857fb1' {

                                ref :>> involved = '2dc4a6c7-e5da-4c4b-b985-c50c84750e56';

                            } 
                        ref action '0b47e37a-cba3-4f2f-a450-d84fbd857fb1' = 'Sense NLG State'; 
                        ref action 'ecd3854f-763d-455b-950e-6252d312040e' = 'Sense Hardware'.'Sense DWNLock Position 2'; 
                        connection '52282344-ef2d-4654-acdd-1055937bc4d1' : FunctionalChainInvolvementLink 
                            connect source ::> 'f5868134-3863-4a3f-afd9-210443cc63de'
                            to  target ::> '0b47e37a-cba3-4f2f-a450-d84fbd857fb1' {

                                ref :>> involved = 'e464a43f-96dd-4638-84e3-50dcae0fc54c';

                            } 
                        ref action 'f5868134-3863-4a3f-afd9-210443cc63de' = 'Sense Hardware'.'Sense DWNLock Position 1'; 
                         
                    }  
                    action 'NLG Uplock Sense' : FunctionalChain  { 
                        @CapellaID { eid = "4aec08f6-dcd9-425c-9249-4422844c4a31"; } 
                        attribute :>> kind = FunctionalChainKind::SIMPLE; 
                        connection 'cac4c993-9003-46e8-bbd8-41b1ed074aa2' : FunctionalChainInvolvementLink 
                            connect source ::> '2e935ac7-d825-4d3a-872f-466e70902c82'
                            to  target ::> 'e4a70956-f11a-4588-8241-3b9d8d2b03b1' {

                                ref :>> involved = '0fe580e4-7e35-48b1-898c-3d7c1f790ec8';

                            } 
                        ref action 'e4a70956-f11a-4588-8241-3b9d8d2b03b1' = 'Sense NLG State'; 
                        ref action '2e935ac7-d825-4d3a-872f-466e70902c82' = 'Sense Hardware'.'Sense NLG Uplock Position 1'; 
                        connection 'd6f4c092-472b-4e15-8cdf-ef59bb3c2ee5' : FunctionalChainInvolvementLink 
                            connect source ::> '906c6f8e-5a11-4e5e-8abc-15ec3c303fa2'
                            to  target ::> 'e4a70956-f11a-4588-8241-3b9d8d2b03b1' {

                                ref :>> involved = '800ff49e-cc73-4b71-9e22-27283841597f';

                            } 
                        ref action '906c6f8e-5a11-4e5e-8abc-15ec3c303fa2' = 'Sense Hardware'.'Sense UPLock Position 2'; 
                         
                    }  
                    action 'Retract and Extend ' : FunctionalChain  { 
                        @CapellaID { eid = "03e7198f-630b-4d5b-b3a9-9113b5254074"; } 
                        attribute :>> kind = FunctionalChainKind::SIMPLE; 
                        connection '252526ac-c5cb-4301-89b9-2929e7bb6a26' : FunctionalChainInvolvementLink 
                            connect source ::> 'd44a6af9-250e-4739-bf82-303c844dd667'
                            to  target ::> 'c78353da-7e4d-4215-acc9-7932b5b0580c' {

                                ref :>> involved = '95abeb94-ee12-44d8-96f4-de9c3e32badf';

                            } 
                        ref action 'c78353da-7e4d-4215-acc9-7932b5b0580c' = 'Measure'.'Actuate NLG'.'Control Pressure to Wheel'; 
                        ref action 'd44a6af9-250e-4739-bf82-303c844dd667' = 'Manage NLG'; 
                        ref action 'da5cf374-7312-4032-888c-0e20c7d7a12c' = 'Measure'.'Actuate NLG'.'Move Gea Up Down'; 
                        connection '5546829e-16b5-4401-b6d6-8a884f1bec29' : FunctionalChainInvolvementLink 
                            connect source ::> 'c78353da-7e4d-4215-acc9-7932b5b0580c'
                            to  target ::> 'da5cf374-7312-4032-888c-0e20c7d7a12c' {

                                ref :>> involved = 'Measure'.'Actuate NLG'.'0667513e-5428-4946-9a4d-299dbb7414f6';

                            } 
                        ref action '4bb31f5a-c6a9-4f1d-8a10-3a6294cc0500' = 'Measure'.'Actuate NLG'.'Apply Force Runway'; 
                        connection 'b404f3c9-891a-4024-a349-bbcaf0515257' : FunctionalChainInvolvementLink 
                            connect source ::> 'da5cf374-7312-4032-888c-0e20c7d7a12c'
                            to  target ::> '4bb31f5a-c6a9-4f1d-8a10-3a6294cc0500' {

                                ref :>> involved = 'Measure'.'Actuate NLG'.'42d8592f-a0d0-48bd-9954-e64ff17fe414';

                            } 
                         
                        ref :>> appliedPropertyValueGroups =  ('SMW Properties'::'Parameters'::'Extension Cycle Time (sec)',
                        'SMW Properties'::'Parameters'::'Retract Cycle Time (sec)'); 
                    }  
                    action 'Support LGP' : FunctionalChain  { 
                        @CapellaID { eid = "a83ca273-6ed3-4d85-b0e7-9a90775fde61"; } 
                        attribute :>> kind = FunctionalChainKind::SIMPLE; 
                        connection '4c8fec7e-1713-42cd-8f13-f5a5875a41cb' : FunctionalChainInvolvementLink 
                            connect source ::> 'b5a8ca82-a344-4bbc-9e8f-75789bcff101'
                            to  target ::> '26c0190f-dc70-42eb-bd55-84d98fc44917' {

                                ref :>> involved = 'e9d0cadd-34a1-4f2d-8be6-334fd4af0052';

                            } 
                        ref action '26c0190f-dc70-42eb-bd55-84d98fc44917' = 'Transmit NLG Forces'.'Transmit NLG Structural Post'; 
                        ref action 'b5a8ca82-a344-4bbc-9e8f-75789bcff101' = 'Support '; 
                        connection 'cd52f7e3-8def-465e-8e12-75186c8b3ac8' : FunctionalChainInvolvementLink 
                            connect source ::> '26c0190f-dc70-42eb-bd55-84d98fc44917'
                            to  target ::> '438e65bb-d35c-4058-9fdc-ec2a4be96c62' {

                                ref :>> involved = '832de532-5107-4edb-a0e5-b610d918034f';

                            } 
                        ref action '438e65bb-d35c-4058-9fdc-ec2a4be96c62' = 'Provide Spring Support'; 
                        connection '907d9232-1080-4735-8163-413d9f7a62f4' : FunctionalChainInvolvementLink 
                            connect source ::> '438e65bb-d35c-4058-9fdc-ec2a4be96c62'
                            to  target ::> 'e6575663-48ca-48e5-b174-1405d06167c4' {

                                ref :>> involved = '1b0e1049-f651-458e-94c5-4381a74f18bb';

                            } 
                        ref action 'e6575663-48ca-48e5-b174-1405d06167c4' = 'Measure'.'Actuate NLG'.'Apply Force Runway'; 
                        connection '13ae4965-93a2-45e0-9e5a-e71b5a3c3553' : FunctionalChainInvolvementLink 
                            connect source ::> 'e6575663-48ca-48e5-b174-1405d06167c4'
                            to  target ::> '1945563e-df8e-4387-ac52-11a2722d8303' {

                                ref :>> involved = '7cee4409-2d70-49cf-9ffa-b6541a64d7e4';

                            } 
                        ref action '1945563e-df8e-4387-ac52-11a2722d8303' = 'Provide Ground  Force'; 
                         
                    }  
                    action 'Supply Hydraulics' : FunctionalChain  { 
                        @CapellaID { eid = "20255ecd-6227-4bd1-9a8f-9258de7ddfed"; } 
                        attribute :>> kind = FunctionalChainKind::SIMPLE; 
                        connection '104b30f7-93de-46f9-8236-cc2e09153258' : FunctionalChainInvolvementLink 
                            connect source ::> '3e1c2989-ebf3-4fb0-b94d-dd620d6c8c65'
                            to  target ::> '8222c09b-cf04-4a74-a2d3-d028781efa28' {

                                ref :>> involved = '59428dfe-81b6-4d97-8654-c1d4bfb73819';

                            } 
                        ref action '8222c09b-cf04-4a74-a2d3-d028781efa28' = 'Measure'.'Actuate NLG'.'Control Pressure to Wheel'; 
                        ref action '3e1c2989-ebf3-4fb0-b94d-dd620d6c8c65' = 'SupplyPressur'; 
                        ref action '761dcab7-22f4-434b-8d6e-6b57960d9f25' = 'Supply Pressure'; 
                        connection '94d685b2-cf36-4b5a-91c2-193af48cb452' : FunctionalChainInvolvementLink 
                            connect source ::> '761dcab7-22f4-434b-8d6e-6b57960d9f25'
                            to  target ::> '3e1c2989-ebf3-4fb0-b94d-dd620d6c8c65' {

                                ref :>> involved = '2ac5535d-5a1f-448f-9a24-cdb778d6e8db';

                            } 
                        ref action '556e2769-aa8e-442b-8ad5-8692bad3abf1' = 'Supply H3 Pressure'; 
                        connection '17bbe8bc-6a27-49d3-add4-613455ce3543' : FunctionalChainInvolvementLink 
                            connect source ::> '556e2769-aa8e-442b-8ad5-8692bad3abf1'
                            to  target ::> '3e1c2989-ebf3-4fb0-b94d-dd620d6c8c65' {

                                ref :>> involved = '41b60723-f7c9-414c-9e34-2b50804b839b';

                            } 
                        ref action '01bb4074-97b7-4daf-9f3e-9938bc6631ac' = 'Actuate RMLG'; 
                        connection '51f9b8ca-094f-4bb4-91ef-2919979398dd' : FunctionalChainInvolvementLink 
                            connect source ::> '3e1c2989-ebf3-4fb0-b94d-dd620d6c8c65'
                            to  target ::> '01bb4074-97b7-4daf-9f3e-9938bc6631ac' {

                                ref :>> involved = 'dee65853-313f-4ca0-974d-7c0587c78f7d';

                            } 
                        ref action '65f89d6e-f53c-468f-9f09-c997daafcfe7' = 'ActuateLMLG'; 
                        connection '1eefa504-e684-4723-aead-4b9e81832c74' : FunctionalChainInvolvementLink 
                            connect source ::> '3e1c2989-ebf3-4fb0-b94d-dd620d6c8c65'
                            to  target ::> '65f89d6e-f53c-468f-9f09-c997daafcfe7' {

                                ref :>> involved = 'b9cdc645-a99b-4cb1-a8c8-5111fdd8db62';

                            } 
                        ref action '4e1d0317-c773-43ac-9795-5620db875a99' = 'Control Pressure'; 
                        connection 'ad4f5618-5506-4c15-bf67-a41d5b4ee6fd' : FunctionalChainInvolvementLink 
                            connect source ::> '3e1c2989-ebf3-4fb0-b94d-dd620d6c8c65'
                            to  target ::> '4e1d0317-c773-43ac-9795-5620db875a99' {

                                ref :>> involved = '58b22acb-b13f-4000-bdf5-222a6006c90c';

                            } 
                        ref action '22902954-1d17-405c-83bd-0b07eb15bd27' = 'Actuate RMLG'; 
                        connection 'db76f85c-4870-4e04-b265-b0fbf49a07b4' : FunctionalChainInvolvementLink 
                            connect source ::> '3e1c2989-ebf3-4fb0-b94d-dd620d6c8c65'
                            to  target ::> '22902954-1d17-405c-83bd-0b07eb15bd27' {

                                ref :>> involved = 'e1a8badb-13d4-4949-b989-39677c7349da';

                            } 
                        ref action '2bd2ccc5-a870-4da4-9f62-bf99550ae9ed' = 'ActuateLMLG'; 
                        connection '45ff1a91-9662-481f-bb2e-5fe41e41b410' : FunctionalChainInvolvementLink 
                            connect source ::> '3e1c2989-ebf3-4fb0-b94d-dd620d6c8c65'
                            to  target ::> '2bd2ccc5-a870-4da4-9f62-bf99550ae9ed' {

                                ref :>> involved = 'cc844e5e-66ad-40b1-b1de-388d7aaafd88';

                            } 
                         
                    }  
                    action 'Deploy and Retract Door' : FunctionalChain  { 
                        @CapellaID { eid = "14966d70-7e48-43f9-86ca-381c6acdcc58"; } 
                        attribute :>> kind = FunctionalChainKind::SIMPLE; 
                        connection '8c65289d-c4d6-4cd8-a34e-01273b5dd6fb' : FunctionalChainInvolvementLink 
                            connect source ::> '7d40c493-25e2-4ee8-80c3-f995ba66e930'
                            to  target ::> '601434bf-2011-4775-8db4-17e0046074fa' {

                                ref :>> involved = '5d56fd8d-edd8-4801-8e3f-c9aa26383600';

                            } 
                        ref action '601434bf-2011-4775-8db4-17e0046074fa' = 'Control Pressure'; 
                        ref action '7d40c493-25e2-4ee8-80c3-f995ba66e930' = 'Manage NLG Door'; 
                        connection '24a25631-7cfd-427b-ba6f-ccbab970cb32' : FunctionalChainInvolvementLink 
                            connect source ::> '601434bf-2011-4775-8db4-17e0046074fa'
                            to  target ::> 'c888923d-4d5a-48ed-a587-5ffe71f601fb' {

                                ref :>> involved = '3fcc6e64-59a4-4362-8a29-7ef25d1d33ef';

                            } 
                        ref action 'c888923d-4d5a-48ed-a587-5ffe71f601fb' = 'Move Door'; 
                         
                    }  
                    action 'Actvate NLG Retract Extend' : FunctionalChain  { 
                        @CapellaID { eid = "cfcea636-c5da-4843-b9b1-85019f0d804a"; } 
                        attribute :>> kind = FunctionalChainKind::SIMPLE; 
                        connection '234f6572-70bf-4d8d-8392-47055ab4ae88' : FunctionalChainInvolvementLink 
                            connect source ::> '332965d1-106f-4f92-aa04-0f9a696ea713'
                            to  target ::> '79083f71-6242-4977-985b-d5cbc0a29679' {

                                ref :>> involved = '01616769-4383-43bc-8c1d-2a6ead7c722f';

                            } 
                        ref action '79083f71-6242-4977-985b-d5cbc0a29679' = 'Provide Landing Gear Control'.'Provide'; 
                        ref action '332965d1-106f-4f92-aa04-0f9a696ea713' = 'Control Gear'; 
                        connection 'fd4403c5-8197-46a5-8a4a-278fb07b9fe9' : FunctionalChainInvolvementLink 
                            connect source ::> '79083f71-6242-4977-985b-d5cbc0a29679'
                            to  target ::> 'd9c57e29-ff99-4d7b-85f5-04bc1aa6bcc0' {

                                ref :>> involved = '4c3fd424-a65e-46d2-8687-718dfacf40e2';

                            } 
                        ref action 'd9c57e29-ff99-4d7b-85f5-04bc1aa6bcc0' = 'Sense NLG State'; 
                         
                    }  
                    action 'NLG Door Overide' : FunctionalChain  { 
                        @CapellaID { eid = "9c2a6430-70c7-4938-99b7-1154cfc5b165"; } 
                        attribute :>> kind = FunctionalChainKind::SIMPLE; 
                        connection '7fb6e342-306b-45bf-879c-7e866a30ece3' : FunctionalChainInvolvementLink 
                            connect source ::> '880f3801-0149-4da6-a376-e6cac8868fbb'
                            to  target ::> 'cc3ff75d-6d7f-42b1-9c9e-623828f3a20b' {

                                ref :>> involved = '49abf19d-43b3-49a7-a4c6-7cfe88216935';

                            } 
                        ref action 'cc3ff75d-6d7f-42b1-9c9e-623828f3a20b' = 'NLG Door Dump'; 
                        ref action '880f3801-0149-4da6-a376-e6cac8868fbb' = 'Nose Landing Gear Library'::'Nose Landing Gear'::'Physical Architecture'::'Physical Functions'::'Root Physical Function'.'NLG Door Overide'; 
                        connection '6a9dbbba-d99e-479b-ad3f-f6c2b5c973dd' : FunctionalChainInvolvementLink 
                            connect source ::> 'cc3ff75d-6d7f-42b1-9c9e-623828f3a20b'
                            to  target ::> 'd52cd4f1-95cf-48c5-8d10-c662edce783c' {

                                ref :>> involved = '8a9a972f-7c53-4fde-8364-eca5e86c5fe5';

                            } 
                        ref action 'd52cd4f1-95cf-48c5-8d10-c662edce783c' = 'Release Door Valve Pressure '; 
                        connection '3d6020ff-bf75-4c3c-a641-529c6d234629' : FunctionalChainInvolvementLink 
                            connect source ::> 'd52cd4f1-95cf-48c5-8d10-c662edce783c'
                            to  target ::> 'e0d70245-42c6-443f-b0a0-82074be84f2d' {

                                ref :>> involved = 'c4b6b216-e81c-4e1b-b059-195564f4e397';

                            } 
                        ref action 'e0d70245-42c6-443f-b0a0-82074be84f2d' = 'Store H Fluid'; 
                         
                    }  
                    action 'NLG Overide' : FunctionalChain  { 
                        @CapellaID { eid = "889f0975-03bb-4e6b-8f06-db782a1659b8"; } 
                        attribute :>> kind = FunctionalChainKind::SIMPLE; 
                        connection '4be9d5ea-3380-4212-8a1f-fa0c1f60eaad' : FunctionalChainInvolvementLink 
                            connect source ::> '2dc1d496-22af-4e0c-9fb1-a96891bbc4aa'
                            to  target ::> 'fc93834e-ff46-49b8-b17b-7a38efedf068' {

                                ref :>> involved = '78c4630d-fda8-439f-abcf-3773df772c00';

                            } 
                        ref action 'fc93834e-ff46-49b8-b17b-7a38efedf068' = 'NLG Dump'; 
                        ref action '2dc1d496-22af-4e0c-9fb1-a96891bbc4aa' = 'NLG Gear Override'; 
                        connection 'f5d0df3c-a424-4a76-8c11-b651af616a3d' : FunctionalChainInvolvementLink 
                            connect source ::> 'fc93834e-ff46-49b8-b17b-7a38efedf068'
                            to  target ::> 'a2b7e476-3a6c-448e-b1b8-f372b82e9b61' {

                                ref :>> involved = 'ecfbd774-e962-4196-a4d1-d8026752c9e5';

                            } 
                        ref action 'a2b7e476-3a6c-448e-b1b8-f372b82e9b61' = 'Release Selector Valve Pressure'; 
                        connection 'ac5565ef-00c1-41f0-b0ad-4a1f1af08a60' : FunctionalChainInvolvementLink 
                            connect source ::> 'a2b7e476-3a6c-448e-b1b8-f372b82e9b61'
                            to  target ::> '654488ad-e1b7-483f-9b17-17490ac7a11d' {

                                ref :>> involved = '3a359c3c-a4a2-411a-8961-29a1bfbea4c6';

                            } 
                        ref action '654488ad-e1b7-483f-9b17-17490ac7a11d' = 'Store H Fluid'; 
                         
                    }  
                    action 'Process Data' : PhysicalFunction  { 
                        @CapellaID { eid = "02702a9b-96a8-46a5-8394-fc745769149e"; sid = "02702a9b-96a8-46a5-8394-fc745769149e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "47dcfa83-3330-4a17-99ca-5c47a8d457f4"; sid = "47dcfa83-3330-4a17-99ca-5c47a8d457f4"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "7b36f80e-1e5a-4fac-8b06-b53ae099f350"; } 
                            attribute :>> isControl = false; 
                            attribute :>> isControlType = false; 
                            attribute :>> kindOfNode = ObjectNodeKind::Unspecified; 
                            attribute :>> ordering = ObjectNodeOrderingKind::FIFO; 
                             
                        }  
                        out port 'FOP 3' : FunctionOutputPort  { 
                            @CapellaID { eid = "17b27958-4470-4694-b5a6-a08454523dac"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "1b1b1459-70d0-4646-b26d-0774efe5e997"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "7a919628-f9a5-48b6-9748-7249f2fa6ef6"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2',
                        'FOP 3'); 
                         
                        ref :>> inputs =  ('FIP 1',
                        'FIP 2'); 
                    }  
                    action 'xmit / xceive' : PhysicalFunction  { 
                        @CapellaID { eid = "fdb9f0e7-d68a-4473-9cf5-c0a2c9a3350c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "7d096ffc-68dd-4e6e-a29b-d4d9ec284bcd"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "f2556870-b3c7-45b2-9132-d61f9105cebd"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Action Report' : PhysicalFunction  { 
                        @CapellaID { eid = "cecaa02a-2c2b-4051-a8e5-8e6cfecb1b3d"; sid = "cecaa02a-2c2b-4051-a8e5-8e6cfecb1b3d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "728a04fc-1f92-4a51-b4d0-94c326f7aa49"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "3ee1113f-8ae5-4d12-9d03-d419ce088a05"; sid = "3ee1113f-8ae5-4d12-9d03-d419ce088a05"; } 
                            attribute :>> isControl = false; 
                            attribute :>> isControlType = false; 
                            attribute :>> kindOfNode = ObjectNodeKind::Unspecified; 
                            attribute :>> ordering = ObjectNodeOrderingKind::FIFO; 
                             
                        }  
                        in port 'inInteraction 20' : FunctionInputPort  { 
                            @CapellaID { eid = "428a1f77-7c0e-447e-a4fe-7e6a71142a59"; sid = "428a1f77-7c0e-447e-a4fe-7e6a71142a59"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2'); 
                         
                        ref :>> inputs =  ('inInteraction 20'); 
                    }  
                    action 'Support Response' : PhysicalFunction  { 
                        @CapellaID { eid = "08b6c786-59af-43f2-803a-3fc72d289e74"; sid = "08b6c786-59af-43f2-803a-3fc72d289e74"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 2' : FunctionOutputPort  { 
                            @CapellaID { eid = "38c5d87e-5583-4faf-8833-f7d7f9800894"; sid = "38c5d87e-5583-4faf-8833-f7d7f9800894"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "48f2a008-9a8e-49dc-b585-fac2a4fbdd7c"; sid = "48f2a008-9a8e-49dc-b585-fac2a4fbdd7c"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "3bdc7024-eb31-4f3f-805a-d3e6e8c95729"; sid = "3bdc7024-eb31-4f3f-805a-d3e6e8c95729"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 2'); 
                         
                        ref :>> inputs =  ('FIP 1',
                        'FIP 2'); 
                    }  
                    action 'Persons Scanned' : PhysicalFunction  { 
                        @CapellaID { eid = "894ec381-cef9-41e6-8c8c-450bd040f143"; sid = "894ec381-cef9-41e6-8c8c-450bd040f143"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "b08d88b5-2cb3-4e73-ae16-4a262de5395b"; sid = "b08d88b5-2cb3-4e73-ae16-4a262de5395b"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                    }  
                    action 'Provide Support' : PhysicalFunction  { 
                        @CapellaID { eid = "95e158e1-c671-4284-b5ff-5e13d76d3721"; sid = "95e158e1-c671-4284-b5ff-5e13d76d3721"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "435f1f97-a7e3-4046-a05d-39b68e57880f"; sid = "435f1f97-a7e3-4046-a05d-39b68e57880f"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "cf805229-a027-47cc-9271-f16e1c9d2c14"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "39a2b353-2e7e-4f81-86a2-3399a2c8f454"; sid = "39a2b353-2e7e-4f81-86a2-3399a2c8f454"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1',
                        'FIP 2'); 
                    }  
                    action 'Interpreted Analysis Response' : PhysicalFunction  { 
                        @CapellaID { eid = "0f2e0551-4f9b-408c-ba4c-2b508c686325"; sid = "0f2e0551-4f9b-408c-ba4c-2b508c686325"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "59ef15ba-1570-4779-8b4f-4fa34521d4b3"; sid = "59ef15ba-1570-4779-8b4f-4fa34521d4b3"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "c3f174a6-9d92-47c9-bd22-49f212a67dd3"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Initiate Mission' : PhysicalFunction  { 
                        @CapellaID { eid = "fed0039a-7aa4-4d79-a63b-f652482b54fb"; sid = "fed0039a-7aa4-4d79-a63b-f652482b54fb"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outInteraction 19' : FunctionOutputPort  { 
                            @CapellaID { eid = "d28f6d35-43f8-4433-b16a-727e079c2618"; sid = "d28f6d35-43f8-4433-b16a-727e079c2618"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('outInteraction 19'); 
                         
                    }  
                    action 'Analysis' : PhysicalFunction  { 
                        @CapellaID { eid = "61f760f4-2a5c-492c-86f4-27016071b65f"; sid = "61f760f4-2a5c-492c-86f4-27016071b65f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "848fc21d-8bbf-436c-8cf0-7fc32210c6a3"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "e8355919-3e50-491f-95c9-3175dfd2edf9"; sid = "e8355919-3e50-491f-95c9-3175dfd2edf9"; } 
                            attribute :>> isControl = false; 
                            attribute :>> isControlType = false; 
                            attribute :>> kindOfNode = ObjectNodeKind::Unspecified; 
                            attribute :>> ordering = ObjectNodeOrderingKind::FIFO; 
                             
                        }  
                        out port 'FOP 3' : FunctionOutputPort  { 
                            @CapellaID { eid = "0375b7f0-6278-4a20-a950-ba9827695897"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "286ab743-84bf-4a00-8e24-d2690c750397"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "4f49c8c8-ec2e-42ef-8be5-5ac87d9d64b5"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2',
                        'FOP 3'); 
                         
                        ref :>> inputs =  ('FIP 1',
                        'FIP 2'); 
                    }  
                    action 'Scan' : PhysicalFunction  { 
                        @CapellaID { eid = "ef307d9b-3357-4caf-96d0-72dfcadfcb35"; sid = "ef307d9b-3357-4caf-96d0-72dfcadfcb35"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 2' : FunctionOutputPort  { 
                            @CapellaID { eid = "b32a31e9-d5c6-426c-b6d7-a661b341007a"; sid = "b32a31e9-d5c6-426c-b6d7-a661b341007a"; } 
                            attribute :>> isControl = false; 
                            attribute :>> isControlType = false; 
                            attribute :>> kindOfNode = ObjectNodeKind::Unspecified; 
                            attribute :>> ordering = ObjectNodeOrderingKind::FIFO; 
                             
                        }  
                        out port 'outInteraction 18' : FunctionOutputPort  { 
                            @CapellaID { eid = "44db790a-db06-4c7c-a982-b493d1387a99"; sid = "44db790a-db06-4c7c-a982-b493d1387a99"; } 
                            attribute :>> isControl = false; 
                            attribute :>> isControlType = false; 
                            attribute :>> kindOfNode = ObjectNodeKind::Unspecified; 
                            attribute :>> ordering = ObjectNodeOrderingKind::FIFO; 
                             
                        }  
                        in port 'inInteraction 19' : FunctionInputPort  { 
                            @CapellaID { eid = "42cc3896-a1f9-4e34-857f-a56837f34dad"; sid = "42cc3896-a1f9-4e34-857f-a56837f34dad"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 2',
                        'outInteraction 18'); 
                         
                        ref :>> inputs =  ('inInteraction 19'); 
                    }  
                    action 'Perform Detect' : PhysicalFunction  { 
                        @CapellaID { eid = "0fffc21b-1bd2-42d6-aca2-df719ff2da5b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Range Detect' : PhysicalFunction  { 
                            @CapellaID { eid = "2c262ef3-fb63-433b-8e12-916bbcaaccfd"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                             
                        }  
                        action 'Locate' : PhysicalFunction  { 
                            @CapellaID { eid = "507b0eb9-96bf-4a35-9aeb-1dc7f2f230ad"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                             
                        }  
                        in port 'FIP 1' : FunctionInputPort  { 
                            @CapellaID { eid = "3de7f5ab-b254-4890-8531-94288fe35bfb"; } 
                            attribute :>> isControl = false; 
                            attribute :>> isControlType = false; 
                            attribute :>> kindOfNode = ObjectNodeKind::Unspecified; 
                            attribute :>> ordering = ObjectNodeOrderingKind::FIFO; 
                             
                        }  
                        in port 'FIP 4' : FunctionInputPort  { 
                            @CapellaID { eid = "b05c5aa8-779a-4141-944d-e485d613caa6"; } 
                            attribute :>> isControl = false; 
                            attribute :>> isControlType = false; 
                            attribute :>> kindOfNode = ObjectNodeKind::Unspecified; 
                            attribute :>> ordering = ObjectNodeOrderingKind::FIFO; 
                             
                        }  
                        ref :>> ownedFunctions =  ('Range Detect',
                        'Locate'); 
                         
                        ref :>> inputs =  ('FIP 1',
                        'FIP 4'); 
                    }  
                    action 'Site Support' : PhysicalFunction  { 
                        @CapellaID { eid = "9d4cafad-2a29-49b6-a12e-9e2ad6a4fe45"; sid = "9d4cafad-2a29-49b6-a12e-9e2ad6a4fe45"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outInteraction 14' : FunctionOutputPort  { 
                            @CapellaID { eid = "fe95a3e4-1da6-415a-b07c-40018092c213"; sid = "fe95a3e4-1da6-415a-b07c-40018092c213"; } 
                            attribute :>> isControl = false; 
                            attribute :>> isControlType = false; 
                            attribute :>> kindOfNode = ObjectNodeKind::Unspecified; 
                            attribute :>> ordering = ObjectNodeOrderingKind::FIFO; 
                             
                        }  
                        out port 'outInteraction 20' : FunctionOutputPort  { 
                            @CapellaID { eid = "7f05f98f-bb3c-4810-932a-f53bb22f6da7"; sid = "7f05f98f-bb3c-4810-932a-f53bb22f6da7"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "a5f01450-be02-4a92-aff0-94bb962f1178"; sid = "a5f01450-be02-4a92-aff0-94bb962f1178"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('outInteraction 14',
                        'outInteraction 20'); 
                         
                        ref :>> inputs =  ('FIP 1'); 
                    }  
                    action 'Persons Supported' : PhysicalFunction  { 
                        @CapellaID { eid = "55683016-5e31-4f39-9fc4-7dbf71d975f3"; sid = "55683016-5e31-4f39-9fc4-7dbf71d975f3"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 2' : FunctionInputPort  { 
                            @CapellaID { eid = "f741c7eb-119b-4a08-9f51-3e94b94e44b9"; sid = "f741c7eb-119b-4a08-9f51-3e94b94e44b9"; } 
                            attribute :>> isControl = false; 
                            attribute :>> isControlType = false; 
                            attribute :>> kindOfNode = ObjectNodeKind::Unspecified; 
                            attribute :>> ordering = ObjectNodeOrderingKind::FIFO; 
                             
                        }  
                        in port 'inInteraction 14' : FunctionInputPort  { 
                            @CapellaID { eid = "6f21edf7-fb41-4e14-90aa-a685cca2d972"; sid = "6f21edf7-fb41-4e14-90aa-a685cca2d972"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('FIP 2',
                        'inInteraction 14'); 
                    }  
                    action 'LOS Control' : PhysicalFunction  { 
                        @CapellaID { eid = "b01d584f-1052-4cb0-a345-9b6282449882"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                         
                    }  
                    action 'BLOS Control' : PhysicalFunction  { 
                        @CapellaID { eid = "469ba42f-7474-4b13-8735-f0ebf7497b71"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                         
                    }  
                    action 'Interpret Analysis' : PhysicalFunction  { 
                        @CapellaID { eid = "7fdf4fcd-afad-4057-89b2-00eb08caf6c5"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "cec1de43-c0b0-4bf2-a065-506df410600b"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "16e0a070-7015-4230-8cec-f5a9cca11eb5"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "1937e81c-39d6-4e92-ba79-78187ec39e6a"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2'); 
                         
                        ref :>> inputs =  ('FIP 1'); 
                    }  
                    action 'Extend Range' : PhysicalFunction  { 
                        @CapellaID { eid = "39996b62-f152-4d13-b29e-145091b5ba03"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Hardened Gear' : PhysicalFunction  { 
                            @CapellaID { eid = "19cb245d-769b-463d-8bf8-85d524308a02"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                             
                        }  
                        action 'Efficient Burn' : PhysicalFunction  { 
                            @CapellaID { eid = "6c423fbf-085d-498e-b2b3-131b58c53497"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                             
                        }  
                        ref :>> ownedFunctions =  ('Hardened Gear',
                        'Efficient Burn'); 
                         
                    }  
                    action 'Monitor Execution' : PhysicalFunction  { 
                        @CapellaID { eid = "b498f7d0-fa5b-4001-a54d-cdbef525b02b"; sid = "b498f7d0-fa5b-4001-a54d-cdbef525b02b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outInteraction 22' : FunctionOutputPort  { 
                            @CapellaID { eid = "34d48828-5695-43fd-9f9f-a58def9d16ff"; sid = "34d48828-5695-43fd-9f9f-a58def9d16ff"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "d4b0c8d5-a3db-4089-84dd-3f420b577610"; sid = "d4b0c8d5-a3db-4089-84dd-3f420b577610"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('outInteraction 22'); 
                         
                        ref :>> inputs =  ('FIP 2'); 
                    }  
                    action 'Update SITREP' : PhysicalFunction  { 
                        @CapellaID { eid = "af05b92f-d4a9-44f9-b220-125ddf90e3ea"; sid = "af05b92f-d4a9-44f9-b220-125ddf90e3ea"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "00d2e6c7-6d6d-494f-a89c-65bf770930da"; sid = "00d2e6c7-6d6d-494f-a89c-65bf770930da"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "31d5bdef-d543-47b0-bcbd-9a660dd99234"; sid = "31d5bdef-d543-47b0-bcbd-9a660dd99234"; } 
                            attribute :>> isControl = false; 
                            attribute :>> isControlType = false; 
                            attribute :>> kindOfNode = ObjectNodeKind::Unspecified; 
                            attribute :>> ordering = ObjectNodeOrderingKind::FIFO; 
                             
                        }  
                        in port 'FIP 4' : FunctionInputPort  { 
                            @CapellaID { eid = "067fefd1-cd68-4c3b-8ddb-1288e72b7a32"; sid = "067fefd1-cd68-4c3b-8ddb-1288e72b7a32"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "9f13d16a-dc53-4a09-8207-6e942d7f6d13"; sid = "9f13d16a-dc53-4a09-8207-6e942d7f6d13"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2'); 
                         
                        ref :>> inputs =  ('FIP 4',
                        'FIP 2'); 
                    }  
                    action 'Interpret SITREP' : PhysicalFunction  { 
                        @CapellaID { eid = "956548e3-564d-4af1-b26b-1c4735eafefe"; sid = "956548e3-564d-4af1-b26b-1c4735eafefe"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "8526432c-7ba5-4da7-bc37-31d248b2da68"; sid = "8526432c-7ba5-4da7-bc37-31d248b2da68"; } 
                            attribute :>> isControl = false; 
                            attribute :>> isControlType = false; 
                            attribute :>> kindOfNode = ObjectNodeKind::Unspecified; 
                            attribute :>> ordering = ObjectNodeOrderingKind::FIFO; 
                             
                        }  
                        in port 'FIP 4' : FunctionInputPort  { 
                            @CapellaID { eid = "410b8ee0-48e3-4842-a6d3-8f4e3eedb284"; sid = "410b8ee0-48e3-4842-a6d3-8f4e3eedb284"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "da7fbb86-e87d-4ea8-9963-023ab00a836f"; sid = "da7fbb86-e87d-4ea8-9963-023ab00a836f"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 4',
                        'FIP 2'); 
                    }  
                    action 'Ad Hoc Mission Update' : PhysicalFunction  { 
                        @CapellaID { eid = "fe5a5c2a-c291-4f67-bae1-63ad28d47aa0"; sid = "fe5a5c2a-c291-4f67-bae1-63ad28d47aa0"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "b1df37ab-d870-4982-a0d8-0ecc0a44d3cd"; sid = "b1df37ab-d870-4982-a0d8-0ecc0a44d3cd"; } 
                            attribute :>> isControl = false; 
                            attribute :>> isControlType = false; 
                            attribute :>> kindOfNode = ObjectNodeKind::Unspecified; 
                            attribute :>> ordering = ObjectNodeOrderingKind::FIFO; 
                             
                        }  
                        in port 'inInteraction 22' : FunctionInputPort  { 
                            @CapellaID { eid = "9f4f86aa-015c-44aa-a79c-9a17c69bfa4c"; sid = "9f4f86aa-015c-44aa-a79c-9a17c69bfa4c"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('inInteraction 22'); 
                    }  
                    action 'Provide C&amp;C SITREP' : PhysicalFunction  { 
                        @CapellaID { eid = "acf8c08a-5924-4458-a484-8d6a16a62d68"; sid = "acf8c08a-5924-4458-a484-8d6a16a62d68"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "b0f0e499-cc9a-435e-bba2-e34e5b0e65c2"; sid = "b0f0e499-cc9a-435e-bba2-e34e5b0e65c2"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "d1fa69a2-f722-467b-9929-6e5de3cc3fd4"; sid = "d1fa69a2-f722-467b-9929-6e5de3cc3fd4"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Ad Hoc Mission Update Response' : PhysicalFunction  { 
                        @CapellaID { eid = "e7dfc4c6-7226-4050-9bbd-007c3b410dd1"; sid = "e7dfc4c6-7226-4050-9bbd-007c3b410dd1"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "13310da0-b306-401c-be3d-ea0ae909fb94"; sid = "13310da0-b306-401c-be3d-ea0ae909fb94"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "08ca01ed-f07b-432c-9cae-499c3f00c7ec"; sid = "08ca01ed-f07b-432c-9cae-499c3f00c7ec"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Ad Hoc Mission Execution Update' : PhysicalFunction  { 
                        @CapellaID { eid = "afcf34e0-09d7-4558-bf0b-d0550e0eebbc"; sid = "afcf34e0-09d7-4558-bf0b-d0550e0eebbc"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "c2c39818-af03-4c86-894f-b2cabffdf4c9"; sid = "c2c39818-af03-4c86-894f-b2cabffdf4c9"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "6ff01767-c9bb-401b-9288-771dbfbe8587"; sid = "6ff01767-c9bb-401b-9288-771dbfbe8587"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Capture Photos' : PhysicalFunction  { 
                        @CapellaID { eid = "428be570-566a-488d-9907-e7fa8a998ae5"; sid = "428be570-566a-488d-9907-e7fa8a998ae5"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outPhotos' : FunctionOutputPort  { 
                            @CapellaID { eid = "9441d746-2a33-46bc-b05a-2e3e0c3774a7"; sid = "9441d746-2a33-46bc-b05a-2e3e0c3774a7"; } 
                            attribute :>> isControl = false; 
                            attribute :>> isControlType = false; 
                            attribute :>> kindOfNode = ObjectNodeKind::Unspecified; 
                            attribute :>> ordering = ObjectNodeOrderingKind::FIFO; 
                             
                        }  
                        in port 'inImage' : FunctionInputPort  { 
                            @CapellaID { eid = "24666314-f21e-451d-a0e4-e2699b7d04e5"; sid = "24666314-f21e-451d-a0e4-e2699b7d04e5"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "97d599a5-dd4a-4e60-9a42-267ccb380de8"; sid = "97d599a5-dd4a-4e60-9a42-267ccb380de8"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('outPhotos'); 
                         
                        ref :>> inputs =  ('inImage',
                        'FIP 2'); 
                    }  
                    action 'Collect Information  Distressed Location ' : PhysicalFunction  { 
                        @CapellaID { eid = "769adc3c-c85e-4e01-b23f-6434e7cb7726"; sid = "769adc3c-c85e-4e01-b23f-6434e7cb7726"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'inRecon Overflight Data' : FunctionInputPort  { 
                            @CapellaID { eid = "7f5ce86a-d6ad-477f-b77b-b27343c47a91"; sid = "7f5ce86a-d6ad-477f-b77b-b27343c47a91"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('inRecon Overflight Data'); 
                    }  
                    action 'Locate Trapped People' : PhysicalFunction  { 
                        @CapellaID { eid = "b19ff0bb-cc9b-46ee-884a-d20717f1c020"; sid = "b19ff0bb-cc9b-46ee-884a-d20717f1c020"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outLocation' : FunctionOutputPort  { 
                            @CapellaID { eid = "d1ed888f-fc60-4f24-8d23-857d15713bb3"; sid = "d1ed888f-fc60-4f24-8d23-857d15713bb3"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "b54e7d66-3229-4ee5-8ed0-4959a13dccad"; sid = "b54e7d66-3229-4ee5-8ed0-4959a13dccad"; } 
                            attribute :>> isControl = false; 
                            attribute :>> isControlType = false; 
                            attribute :>> kindOfNode = ObjectNodeKind::Unspecified; 
                            attribute :>> ordering = ObjectNodeOrderingKind::FIFO; 
                             
                        }  
                        in port 'inImages of trapped People' : FunctionInputPort  { 
                            @CapellaID { eid = "8401bf68-4638-432b-9698-0bb8fa791796"; sid = "8401bf68-4638-432b-9698-0bb8fa791796"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('outLocation',
                        'FOP 2'); 
                         
                        ref :>> inputs =  ('inImages of trapped People'); 
                    }  
                    action 'Capture Video' : PhysicalFunction  { 
                        @CapellaID { eid = "8e687b1d-18f2-4103-955a-fbc3d8dd5364"; sid = "8e687b1d-18f2-4103-955a-fbc3d8dd5364"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outVideo' : FunctionOutputPort  { 
                            @CapellaID { eid = "dcc25b10-6b48-4be6-95ad-d7d025db1430"; sid = "dcc25b10-6b48-4be6-95ad-d7d025db1430"; } 
                            attribute :>> isControl = false; 
                            attribute :>> isControlType = false; 
                            attribute :>> kindOfNode = ObjectNodeKind::Unspecified; 
                            attribute :>> ordering = ObjectNodeOrderingKind::FIFO; 
                             
                        }  
                        in port 'inAudio Visual' : FunctionInputPort  { 
                            @CapellaID { eid = "ce1ddf9c-423f-4ebc-9e79-162ef35353b2"; sid = "ce1ddf9c-423f-4ebc-9e79-162ef35353b2"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "d457ea9a-bee2-4697-992e-0ca9849243db"; sid = "d457ea9a-bee2-4697-992e-0ca9849243db"; } 
                            attribute :>> isControl = false; 
                            attribute :>> isControlType = false; 
                            attribute :>> kindOfNode = ObjectNodeKind::Unspecified; 
                            attribute :>> ordering = ObjectNodeOrderingKind::FIFO; 
                             
                        }  
                        in port 'FIP 3' : FunctionInputPort  { 
                            @CapellaID { eid = "92c0f2b8-0c6e-4bbf-9de0-4f34e0678a22"; sid = "92c0f2b8-0c6e-4bbf-9de0-4f34e0678a22"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('outVideo'); 
                         
                        ref :>> inputs =  ('inAudio Visual',
                        'FIP 2',
                        'FIP 3'); 
                    }  
                    action 'Natural Disaster ' : PhysicalFunction  { 
                        @CapellaID { eid = "049f4592-54be-4ea2-93b3-c97c2a41599e"; sid = "049f4592-54be-4ea2-93b3-c97c2a41599e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outImage' : FunctionOutputPort  { 
                            @CapellaID { eid = "2b6f72e5-44c0-4d0e-b7bc-ad3036b0f318"; sid = "2b6f72e5-44c0-4d0e-b7bc-ad3036b0f318"; } 
                            attribute :>> isControl = false; 
                            attribute :>> isControlType = false; 
                            attribute :>> kindOfNode = ObjectNodeKind::Unspecified; 
                            attribute :>> ordering = ObjectNodeOrderingKind::FIFO; 
                             
                        }  
                        out port 'outAudio Visual' : FunctionOutputPort  { 
                            @CapellaID { eid = "b499f4ee-1d27-4d3e-866a-f8d3a9017933"; sid = "b499f4ee-1d27-4d3e-866a-f8d3a9017933"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('outImage',
                        'outAudio Visual'); 
                         
                    }  
                    action 'Define Overflight Recon Mission' : PhysicalFunction  { 
                        @CapellaID { eid = "9c7374b9-b198-4dc9-8f88-f8e1d7669723"; sid = "9c7374b9-b198-4dc9-8f88-f8e1d7669723"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outMIssion' : FunctionOutputPort  { 
                            @CapellaID { eid = "e7a1a912-4ac4-4b67-b53e-4d909d2fa0ed"; sid = "e7a1a912-4ac4-4b67-b53e-4d909d2fa0ed"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('outMIssion'); 
                         
                    }  
                    action 'Relay Overflight Data from Drone Mission' : PhysicalFunction  { 
                        @CapellaID { eid = "c9fe98ba-eb21-4faf-8ccd-827b742ebcf0"; sid = "c9fe98ba-eb21-4faf-8ccd-827b742ebcf0"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outRecon Overflight Data' : FunctionOutputPort  { 
                            @CapellaID { eid = "6420e768-91f4-4fca-b66a-45db3c5f7504"; sid = "6420e768-91f4-4fca-b66a-45db3c5f7504"; } 
                            attribute :>> isControl = false; 
                            attribute :>> isControlType = false; 
                            attribute :>> kindOfNode = ObjectNodeKind::Unspecified; 
                            attribute :>> ordering = ObjectNodeOrderingKind::FIFO; 
                             
                        }  
                        in port 'inLocation' : FunctionInputPort  { 
                            @CapellaID { eid = "c8dd6e1d-91dd-4b8f-89fb-02ff6bfe29a7"; sid = "c8dd6e1d-91dd-4b8f-89fb-02ff6bfe29a7"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "b708fed3-bdbc-4549-83ad-8cb22070115d"; sid = "b708fed3-bdbc-4549-83ad-8cb22070115d"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('outRecon Overflight Data'); 
                         
                        ref :>> inputs =  ('inLocation',
                        'FIP 2'); 
                    }  
                    action 'Perform Overflight Recon Mission' : PhysicalFunction  { 
                        @CapellaID { eid = "fb292115-88dd-48c1-bee8-9229078f69fe"; sid = "fb292115-88dd-48c1-bee8-9229078f69fe"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Perform Scan' : PhysicalFunction  { 
                            @CapellaID { eid = "7ab58ffa-f766-46fa-8f40-a1bba0477ff5"; sid = "7ab58ffa-f766-46fa-8f40-a1bba0477ff5"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "eef85bc3-f6d2-4414-8c99-67635653cb99"; sid = "eef85bc3-f6d2-4414-8c99-67635653cb99"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "049f5a93-545f-48ec-9634-d7c570398a6b"; sid = "049f5a93-545f-48ec-9634-d7c570398a6b"; } 
                                attribute :>> isControl = false; 
                                attribute :>> isControlType = false; 
                                attribute :>> kindOfNode = ObjectNodeKind::Unspecified; 
                                attribute :>> ordering = ObjectNodeOrderingKind::FIFO; 
                                 
                            }  
                            in port 'FIP 2' : FunctionInputPort  { 
                                @CapellaID { eid = "cfee12f3-707e-4f6b-bd8e-d73208d61586"; sid = "cfee12f3-707e-4f6b-bd8e-d73208d61586"; } 
                                attribute :>> isControl = false; 
                                attribute :>> isControlType = false; 
                                attribute :>> kindOfNode = ObjectNodeKind::Unspecified; 
                                attribute :>> ordering = ObjectNodeOrderingKind::FIFO; 
                                 
                            }  
                            in port 'FIP 3' : FunctionInputPort  { 
                                @CapellaID { eid = "69cc6024-7ade-430b-ac88-38cabb520353"; sid = "69cc6024-7ade-430b-ac88-38cabb520353"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 1'); 
                             
                            ref :>> inputs =  ('FIP 1',
                            'FIP 2',
                            'FIP 3'); 
                        }  
                        in port 'inMIssion' : FunctionInputPort  { 
                            @CapellaID { eid = "256c4c68-dafb-4d81-a2db-4d9da4cf8bc3"; sid = "256c4c68-dafb-4d81-a2db-4d9da4cf8bc3"; } 
                            attribute :>> isControl = false; 
                            attribute :>> isControlType = false; 
                            attribute :>> kindOfNode = ObjectNodeKind::Unspecified; 
                            attribute :>> ordering = ObjectNodeOrderingKind::FIFO; 
                             
                        }  
                        ref :>> ownedFunctions =  ('Perform Scan'); 
                         
                        ref :>> inputs =  ('inMIssion'); 
                    }  
                    action 'Relay to Operator' : PhysicalFunction  { 
                        @CapellaID { eid = "3474bb94-85ad-4045-ad36-59a3a536b6ce"; sid = "3474bb94-85ad-4045-ad36-59a3a536b6ce"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "8186d964-4aba-46d5-b56d-e1f141c686a8"; sid = "8186d964-4aba-46d5-b56d-e1f141c686a8"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "6fe3c68a-4e80-47a3-a090-3e6f888996ec"; sid = "6fe3c68a-4e80-47a3-a090-3e6f888996ec"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 2'); 
                    }  
                    action 'Gather 35' : PhysicalFunction  { 
                        @CapellaID { eid = "e30bec3b-0242-4c5d-a1ba-ff6b117d924b"; sid = "e30bec3b-0242-4c5d-a1ba-ff6b117d924b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::GATHER; 
                        attribute :>> isMaxInclusive = false; 
                        attribute :>> isMinInclusive = false; 
                        attribute :>> isOrdered = false; 
                        attribute :>> isUnique = false; 
                        out port 'FOP 1' : FunctionOutputPort  { 
                            @CapellaID { eid = "f1e86192-1e92-4c53-81d8-555dd5727158"; sid = "f1e86192-1e92-4c53-81d8-555dd5727158"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "e448a89d-9c8a-4f23-a536-57a6adef85ce"; sid = "e448a89d-9c8a-4f23-a536-57a6adef85ce"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Operator Mission Planning' : PhysicalFunction  { 
                        @CapellaID { eid = "438e117e-3425-4b78-b7a6-6083c9505926"; sid = "438e117e-3425-4b78-b7a6-6083c9505926"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "84c862bc-8de2-43c9-9b9f-f20ab0d345e5"; sid = "84c862bc-8de2-43c9-9b9f-f20ab0d345e5"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "a8d0a82e-bbc8-450c-ba1e-fc32d52c07a5"; sid = "a8d0a82e-bbc8-450c-ba1e-fc32d52c07a5"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Receive Mission Order' : PhysicalFunction  { 
                        @CapellaID { eid = "d1807936-f762-46ad-be2e-629582c8ab75"; sid = "d1807936-f762-46ad-be2e-629582c8ab75"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "eea37229-d798-45ba-9365-ac4601f12f5c"; sid = "eea37229-d798-45ba-9365-ac4601f12f5c"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                    }  
                    action 'Activate Scan' : PhysicalFunction  { 
                        @CapellaID { eid = "35334f9f-729b-47a2-b7d0-8982567a75e9"; sid = "35334f9f-729b-47a2-b7d0-8982567a75e9"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::SPLIT; 
                        attribute :>> isMaxInclusive = false; 
                        attribute :>> isMinInclusive = false; 
                        attribute :>> isOrdered = false; 
                        attribute :>> isUnique = false; 
                        out port 'FOP 1' : FunctionOutputPort  { 
                            @CapellaID { eid = "1c13ec15-d03b-4643-9212-3737efe6610b"; sid = "1c13ec15-d03b-4643-9212-3737efe6610b"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "9063018d-d33f-4397-b601-68fa1ea63d9b"; sid = "9063018d-d33f-4397-b601-68fa1ea63d9b"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "5c90b577-cfa0-4114-8999-97b4c0e6283b"; sid = "5c90b577-cfa0-4114-8999-97b4c0e6283b"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2'); 
                         
                        ref :>> inputs =  ('FIP 2'); 
                    }  
                    action 'Image Storage' : PhysicalFunction  { 
                        @CapellaID { eid = "c991b9dd-8b14-4da7-a8cc-e0caf8d216bc"; sid = "c991b9dd-8b14-4da7-a8cc-e0caf8d216bc"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outImages of trapped People' : FunctionOutputPort  { 
                            @CapellaID { eid = "247149d1-28ce-4cf1-a256-fd62f2bcafac"; sid = "247149d1-28ce-4cf1-a256-fd62f2bcafac"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "092c6dd8-d79f-4cbd-9a6b-626f7f69ea56"; sid = "092c6dd8-d79f-4cbd-9a6b-626f7f69ea56"; } 
                            attribute :>> isControl = false; 
                            attribute :>> isControlType = false; 
                            attribute :>> kindOfNode = ObjectNodeKind::Unspecified; 
                            attribute :>> ordering = ObjectNodeOrderingKind::FIFO; 
                             
                        }  
                        in port 'inPhotos' : FunctionInputPort  { 
                            @CapellaID { eid = "ebf4413d-814d-4c89-a3de-6cc51593a348"; sid = "ebf4413d-814d-4c89-a3de-6cc51593a348"; } 
                            attribute :>> isControl = false; 
                            attribute :>> isControlType = false; 
                            attribute :>> kindOfNode = ObjectNodeKind::Unspecified; 
                            attribute :>> ordering = ObjectNodeOrderingKind::FIFO; 
                             
                        }  
                        in port 'inVideo' : FunctionInputPort  { 
                            @CapellaID { eid = "0b7bca40-caf4-4f22-a256-2896187d27d0"; sid = "0b7bca40-caf4-4f22-a256-2896187d27d0"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('outImages of trapped People',
                        'FOP 2'); 
                         
                        ref :>> inputs =  ('inPhotos',
                        'inVideo'); 
                    }  
                    action 'PhysicalFunction 39' : PhysicalFunction  { 
                        @CapellaID { eid = "bb894742-9a27-41aa-a010-c7fb5a47593f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "7ee7a800-6e15-45dd-97b7-41fcfd6e0661"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "e01b76ec-d6b8-4675-bb75-16a13b7f4aac"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'PhysicalFunction 40' : PhysicalFunction  { 
                        @CapellaID { eid = "80c805ac-7d15-4b5b-9a4e-f9db1440a89d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "bf3f6bf3-e325-4d12-bc6c-5d7c3d1647ff"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "7b479a7a-e1bc-45b0-a2c6-db913cb8c3c8"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'PhysicalFunction 41' : PhysicalFunction  { 
                        @CapellaID { eid = "a6e09543-353d-4a07-8a33-42583659c5ef"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "7b215f6e-9f18-4928-8a03-76a0767aad3e"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                    }  
                    action 'Supply H3 Pressure' : PhysicalFunction  { 
                        @CapellaID { eid = "e6fbf02b-7ead-4c6e-8643-bda8dab17811"; sid = "e6fbf02b-7ead-4c6e-8643-bda8dab17811"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "ecf341a5-5b9c-4286-8206-0fe8303173c5"; sid = "ecf341a5-5b9c-4286-8206-0fe8303173c5"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "4e0c6d2a-9db5-43b8-a4ec-fa547881f622"; sid = "4e0c6d2a-9db5-43b8-a4ec-fa547881f622"; } 
                            attribute :>> isControl = false; 
                            attribute :>> isControlType = false; 
                            attribute :>> kindOfNode = ObjectNodeKind::Unspecified; 
                            attribute :>> ordering = ObjectNodeOrderingKind::FIFO; 
                             
                        }  
                        out port 'FOP 3' : FunctionOutputPort  { 
                            @CapellaID { eid = "5a276e38-00f9-40ae-ad2e-c1cb2b5f59a0"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "2f04a6be-8657-4d27-a213-9897c3e46540"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "1ea8ea93-40a7-40a1-8df7-b78f33302f3c"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2',
                        'FOP 3'); 
                         
                        ref :>> inputs =  ('FIP 1',
                        'FIP 2'); 
                    }  
                    action 'Measure' : PhysicalFunction  { 
                        @CapellaID { eid = "96fc0e5a-31f7-4681-8b39-a078464bad6b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Actuate NLG' : PhysicalFunction  { 
                            @CapellaID { eid = "3695618d-cf0d-4f63-95ba-89a1e1990e28"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            action 'Control Pressure to Wheel' : PhysicalFunction  { 
                                @CapellaID { eid = "33563d08-1277-4dd3-b227-2793d687b1cf"; sid = "33563d08-1277-4dd3-b227-2793d687b1cf"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = FunctionKind::FUNCTION; 
                                attribute :>> isMaxInclusive = false; 
                                attribute :>> isMinInclusive = false; 
                                attribute :>> isOrdered = false; 
                                attribute :>> isUnique = false; 
                                out port 'FOP 1' : FunctionOutputPort  { 
                                    @CapellaID { eid = "00e48a67-d7bd-4cc0-8c9f-e8c12dec360d"; sid = "00e48a67-d7bd-4cc0-8c9f-e8c12dec360d"; } 
                                    attribute :>> isControl = false; 
                                    attribute :>> isControlType = false; 
                                    attribute :>> kindOfNode = ObjectNodeKind::Unspecified; 
                                    attribute :>> ordering = ObjectNodeOrderingKind::FIFO; 
                                     
                                }  
                                out port 'FOP 7' : FunctionOutputPort  { 
                                    @CapellaID { eid = "89c4cec9-f192-48a4-9bc4-ac91e4305eeb"; } 
                                    attribute :>> isControl = false; 
                                    attribute :>> isControlType = false; 
                                    attribute :>> kindOfNode = ObjectNodeKind::Unspecified; 
                                    attribute :>> ordering = ObjectNodeOrderingKind::FIFO; 
                                     
                                }  
                                in port 'FIP 1' : FunctionInputPort  { 
                                    @CapellaID { eid = "9de124c5-29d7-4b32-a016-9f35e84f9909"; sid = "9de124c5-29d7-4b32-a016-9f35e84f9909"; } 
                                    attribute :>> isControl = false; 
                                    attribute :>> isControlType = false; 
                                    attribute :>> kindOfNode = ObjectNodeKind::Unspecified; 
                                    attribute :>> ordering = ObjectNodeOrderingKind::FIFO; 
                                     
                                }  
                                in port 'FIP 3' : FunctionInputPort  { 
                                    @CapellaID { eid = "2a41a494-3e12-4707-8117-8dee59e57e83"; sid = "2a41a494-3e12-4707-8117-8dee59e57e83"; } 
                                    attribute :>> isControl = false; 
                                    attribute :>> isControlType = false; 
                                    attribute :>> kindOfNode = ObjectNodeKind::Unspecified; 
                                    attribute :>> ordering = ObjectNodeOrderingKind::FIFO; 
                                     
                                }  
                                ref :>> outputs =  ('FOP 1',
                                'FOP 7'); 
                                 
                                ref :>> inputs =  ('FIP 1',
                                'FIP 3'); 
                            }  
                            action 'Move Gea Up Down' : PhysicalFunction  { 
                                @CapellaID { eid = "30b1a548-c9f4-41d3-8785-4b32c480e977"; sid = "30b1a548-c9f4-41d3-8785-4b32c480e977"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = FunctionKind::FUNCTION; 
                                attribute :>> isMaxInclusive = false; 
                                attribute :>> isMinInclusive = false; 
                                attribute :>> isOrdered = false; 
                                attribute :>> isUnique = false; 
                                out port 'FOP 1' : FunctionOutputPort  { 
                                    @CapellaID { eid = "cbbde145-9941-42a4-aaed-20451d1a4c75"; sid = "cbbde145-9941-42a4-aaed-20451d1a4c75"; } 
                                    attribute :>> isControl = false; 
                                    attribute :>> isControlType = false; 
                                    attribute :>> kindOfNode = ObjectNodeKind::Unspecified; 
                                    attribute :>> ordering = ObjectNodeOrderingKind::FIFO; 
                                     
                                }  
                                in port 'FIP 1' : FunctionInputPort  { 
                                    @CapellaID { eid = "1590b761-6fc5-4ced-afbd-ad986b1264b7"; sid = "1590b761-6fc5-4ced-afbd-ad986b1264b7"; } 
                                    attribute :>> isControl = false; 
                                    attribute :>> isControlType = false; 
                                    attribute :>> kindOfNode = ObjectNodeKind::Unspecified; 
                                    attribute :>> ordering = ObjectNodeOrderingKind::FIFO; 
                                     
                                }  
                                ref :>> outputs =  ('FOP 1'); 
                                 
                                ref :>> inputs =  ('FIP 1'); 
                            }  
                            action 'Apply Force Runway' : PhysicalFunction  { 
                                @CapellaID { eid = "6ff3f54d-e918-4b43-9f5f-07950c373de4"; sid = "6ff3f54d-e918-4b43-9f5f-07950c373de4"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = FunctionKind::FUNCTION; 
                                attribute :>> isMaxInclusive = false; 
                                attribute :>> isMinInclusive = false; 
                                attribute :>> isOrdered = false; 
                                attribute :>> isUnique = false; 
                                out port 'FOP 1' : FunctionOutputPort  { 
                                    @CapellaID { eid = "3d008922-3096-439e-aef1-6146f783881e"; sid = "3d008922-3096-439e-aef1-6146f783881e"; } 
                                    attribute :>> isControl = false; 
                                    attribute :>> isControlType = false; 
                                    attribute :>> kindOfNode = ObjectNodeKind::Unspecified; 
                                    attribute :>> ordering = ObjectNodeOrderingKind::FIFO; 
                                     
                                }  
                                out port 'FOP 3' : FunctionOutputPort  { 
                                    @CapellaID { eid = "c7fba890-08dc-47a0-826d-f0027c9b8f6b"; sid = "c7fba890-08dc-47a0-826d-f0027c9b8f6b"; } 
                                    attribute :>> isControl = false; 
                                    attribute :>> isControlType = false; 
                                    attribute :>> kindOfNode = ObjectNodeKind::Unspecified; 
                                    attribute :>> ordering = ObjectNodeOrderingKind::FIFO; 
                                     
                                }  
                                in port 'FIP 1' : FunctionInputPort  { 
                                    @CapellaID { eid = "9cbd803e-25fb-4cc0-89e6-87fa38bc15ab"; sid = "9cbd803e-25fb-4cc0-89e6-87fa38bc15ab"; } 
                                    attribute :>> isControl = false; 
                                    attribute :>> isControlType = false; 
                                    attribute :>> kindOfNode = ObjectNodeKind::Unspecified; 
                                    attribute :>> ordering = ObjectNodeOrderingKind::FIFO; 
                                     
                                }  
                                in port 'FIP 2' : FunctionInputPort  { 
                                    @CapellaID { eid = "bb3996ab-204b-4ab5-a85f-42335ff7cc71"; } 
                                    attribute :>> isControl = false; 
                                    attribute :>> isControlType = false; 
                                    attribute :>> kindOfNode = ObjectNodeKind::Unspecified; 
                                    attribute :>> ordering = ObjectNodeOrderingKind::FIFO; 
                                     
                                }  
                                ref :>> outputs =  ('FOP 1',
                                'FOP 3'); 
                                 
                                ref :>> inputs =  ('FIP 1',
                                'FIP 2'); 
                            }  
                            interface '0667513e-5428-4946-9a4d-299dbb7414f6' : FunctionalExchange 
                                connect source ::> 'Control Pressure to Wheel'.'FOP 1'
                                to target ::> 'Move Gea Up Down'.'FIP 1' { 
                                @CapellaID { eid = "0667513e-5428-4946-9a4d-299dbb7414f6"; sid = "0667513e-5428-4946-9a4d-299dbb7414f6"; } 
                                attribute :>> isMulticast = false; 
                                attribute :>> isMultireceive = false; 
                                attribute :>> kindOfRate = RateKind::Unspecified; 
                                attribute :>> interfaceName = "Hydraulic"; 
                                 
                            }  
                            interface '42d8592f-a0d0-48bd-9954-e64ff17fe414' : FunctionalExchange 
                                connect source ::> 'Move Gea Up Down'.'FOP 1'
                                to target ::> 'Apply Force Runway'.'FIP 1' { 
                                @CapellaID { eid = "42d8592f-a0d0-48bd-9954-e64ff17fe414"; sid = "42d8592f-a0d0-48bd-9954-e64ff17fe414"; } 
                                attribute :>> isMulticast = false; 
                                attribute :>> isMultireceive = false; 
                                attribute :>> kindOfRate = RateKind::Unspecified; 
                                attribute :>> interfaceName = "Force"; 
                                 
                            }  
                            ref :>> ownedFunctions =  ('Control Pressure to Wheel',
                            'Move Gea Up Down',
                            'Apply Force Runway'); 
                             
                            ref :>> ownedFunctionalExchanges =  ('0667513e-5428-4946-9a4d-299dbb7414f6',
                            '42d8592f-a0d0-48bd-9954-e64ff17fe414'); 
                        }  
                        in port 'FIP 2' : FunctionInputPort  { 
                            @CapellaID { eid = "294f8ff2-f83a-4c37-9e0a-a2d6a5caabd6"; } 
                            attribute :>> isControl = false; 
                            attribute :>> isControlType = false; 
                            attribute :>> kindOfNode = ObjectNodeKind::Unspecified; 
                            attribute :>> ordering = ObjectNodeOrderingKind::FIFO; 
                             
                        }  
                        ref :>> ownedFunctions =  ('Actuate NLG'); 
                         
                        ref :>> inputs =  ('FIP 2'); 
                    }  
                    action 'Provide Landing Gear Control' : PhysicalFunction  { 
                        @CapellaID { eid = "52fc835c-492c-42a2-b749-6d0e6b634982"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Provide' : PhysicalFunction  { 
                            @CapellaID { eid = "1f2fbbb2-efee-4749-ba5d-9f98ffeca051"; sid = "1f2fbbb2-efee-4749-ba5d-9f98ffeca051"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "e90e8dd5-7bd8-4f57-9703-363a4094f06b"; sid = "e90e8dd5-7bd8-4f57-9703-363a4094f06b"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "c6fd3a69-fb2d-414c-bc75-e17215bc7556"; } 
                                attribute :>> isControl = false; 
                                attribute :>> isControlType = false; 
                                attribute :>> kindOfNode = ObjectNodeKind::Unspecified; 
                                attribute :>> ordering = ObjectNodeOrderingKind::FIFO; 
                                 
                            }  
                            in port 'FIP 2' : FunctionInputPort  { 
                                @CapellaID { eid = "78ee7690-9525-40d2-8219-66530f0890cb"; } 
                                attribute :>> isControl = false; 
                                attribute :>> isControlType = false; 
                                attribute :>> kindOfNode = ObjectNodeKind::Unspecified; 
                                attribute :>> ordering = ObjectNodeOrderingKind::FIFO; 
                                 
                            }  
                            in port 'FIP 3' : FunctionInputPort  { 
                                @CapellaID { eid = "077b8a57-32fd-4635-9cbd-b4cc71d2e7e0"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 1'); 
                             
                            ref :>> inputs =  ('FIP 1',
                            'FIP 2',
                            'FIP 3'); 
                        }  
                        ref :>> ownedFunctions =  ('Provide'); 
                         
                    }  
                    action 'Provide Landing Gear Indication' : PhysicalFunction  { 
                        @CapellaID { eid = "512d2990-6a53-4e1a-81dc-c37d32a2e33f"; sid = "512d2990-6a53-4e1a-81dc-c37d32a2e33f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Provide' : PhysicalFunction  { 
                            @CapellaID { eid = "2b79bf8e-2372-4b63-852c-15b5b4f9d320"; sid = "2b79bf8e-2372-4b63-852c-15b5b4f9d320"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "600743ce-a886-4d62-a342-7ab303cd4e4d"; sid = "600743ce-a886-4d62-a342-7ab303cd4e4d"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "19f9e20a-5861-42b3-89c8-42fa533e8104"; sid = "19f9e20a-5861-42b3-89c8-42fa533e8104"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 1'); 
                             
                            ref :>> inputs =  ('FIP 1'); 
                        }  
                        ref :>> ownedFunctions =  ('Provide'); 
                         
                    }  
                    action 'Sense Pressure' : PhysicalFunction  { 
                        @CapellaID { eid = "f7c8f2f7-8cd8-440f-9b22-66bf597a86f4"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "9c245f90-eeaa-4dfd-b35a-71744401f393"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                    }  
                    action 'Provide' : PhysicalFunction  { 
                        @CapellaID { eid = "9a763916-84b2-4693-8a2f-7672a1f2daa9"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "9a4f8318-8e2f-4cf7-9890-dfcd50cb0233"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                    }  
                    action 'Support ' : PhysicalFunction  { 
                        @CapellaID { eid = "f69da8ef-5c9f-49d6-a0b0-852194ccd7aa"; sid = "f69da8ef-5c9f-49d6-a0b0-852194ccd7aa"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "37bab8a1-0ba4-4d2b-8f08-32960ab8e6df"; sid = "37bab8a1-0ba4-4d2b-8f08-32960ab8e6df"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "0ebd3473-fc12-49b2-97fe-0cddbb40ca6a"; sid = "0ebd3473-fc12-49b2-97fe-0cddbb40ca6a"; } 
                            attribute :>> isControl = false; 
                            attribute :>> isControlType = false; 
                            attribute :>> kindOfNode = ObjectNodeKind::Unspecified; 
                            attribute :>> ordering = ObjectNodeOrderingKind::FIFO; 
                             
                        }  
                        out port 'FOP 3' : FunctionOutputPort  { 
                            @CapellaID { eid = "15105280-f4aa-40dd-bd9f-5f5138f555b9"; } 
                            attribute :>> isControl = false; 
                            attribute :>> isControlType = false; 
                            attribute :>> kindOfNode = ObjectNodeKind::Unspecified; 
                            attribute :>> ordering = ObjectNodeOrderingKind::FIFO; 
                             
                        }  
                        in port 'FIP 4' : FunctionInputPort  { 
                            @CapellaID { eid = "8ceebe23-eabe-4fbe-b29a-f6c1087c53c5"; sid = "8ceebe23-eabe-4fbe-b29a-f6c1087c53c5"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2',
                        'FOP 3'); 
                         
                        ref :>> inputs =  ('FIP 4'); 
                    }  
                    action 'Transmit LG Force' : PhysicalFunction  { 
                        @CapellaID { eid = "dec30c6a-e4de-446c-a020-36733e3a9916"; sid = "dec30c6a-e4de-446c-a020-36733e3a9916"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "ab155cb3-3fdc-49d2-bcaf-c0738869f545"; sid = "ab155cb3-3fdc-49d2-bcaf-c0738869f545"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "cad75b94-94a7-4776-808f-50054eb1055a"; sid = "cad75b94-94a7-4776-808f-50054eb1055a"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "8dbe6fbd-0c27-45d4-ab55-8a76454ebd07"; sid = "8dbe6fbd-0c27-45d4-ab55-8a76454ebd07"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1',
                        'FIP 2'); 
                    }  
                    action 'Provide Status' : PhysicalFunction  { 
                        @CapellaID { eid = "38506092-97df-4315-af71-c73271f6ab7e"; sid = "38506092-97df-4315-af71-c73271f6ab7e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "d5082121-e375-4411-a959-47b4b6123b4a"; sid = "d5082121-e375-4411-a959-47b4b6123b4a"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('FIP 1'); 
                    }  
                    action 'Provide Ground  Force' : PhysicalFunction  { 
                        @CapellaID { eid = "5d7ed92d-2d5c-4963-8706-ac5761bffd66"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "c5745008-4690-4822-b1bc-49cd18d1ae58"; } 
                            attribute :>> isControl = false; 
                            attribute :>> isControlType = false; 
                            attribute :>> kindOfNode = ObjectNodeKind::Unspecified; 
                            attribute :>> ordering = ObjectNodeOrderingKind::FIFO; 
                             
                        }  
                        in port 'FIP 3' : FunctionInputPort  { 
                            @CapellaID { eid = "b0eed6ba-b810-4797-ba4c-9fc8aaa66252"; } 
                            attribute :>> isControl = false; 
                            attribute :>> isControlType = false; 
                            attribute :>> kindOfNode = ObjectNodeKind::Unspecified; 
                            attribute :>> ordering = ObjectNodeOrderingKind::FIFO; 
                             
                        }  
                        in port 'FIP 4' : FunctionInputPort  { 
                            @CapellaID { eid = "e9600e10-2b09-4de3-85fa-4df933e231a3"; sid = "e9600e10-2b09-4de3-85fa-4df933e231a3"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('FIP 1',
                        'FIP 3',
                        'FIP 4'); 
                    }  
                    action 'Provide Friction' : PhysicalFunction  { 
                        @CapellaID { eid = "0d244865-5bae-4379-97aa-b1ebf7c3e729"; sid = "0d244865-5bae-4379-97aa-b1ebf7c3e729"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "319cd60a-838a-4c84-b6cf-c501d45bdcc0"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "b20a7dce-2100-43ed-b99f-3dbd55d93859"; } 
                            attribute :>> isControl = false; 
                            attribute :>> isControlType = false; 
                            attribute :>> kindOfNode = ObjectNodeKind::Unspecified; 
                            attribute :>> ordering = ObjectNodeOrderingKind::FIFO; 
                             
                        }  
                        in port 'FIP 3' : FunctionInputPort  { 
                            @CapellaID { eid = "85ef1054-08d3-4ed6-af8f-e19b25b1b84f"; } 
                            attribute :>> isControl = false; 
                            attribute :>> isControlType = false; 
                            attribute :>> kindOfNode = ObjectNodeKind::Unspecified; 
                            attribute :>> ordering = ObjectNodeOrderingKind::FIFO; 
                             
                        }  
                        in port 'FIP 5' : FunctionInputPort  { 
                            @CapellaID { eid = "b2e9e0fc-28a1-4d90-ac9e-65d7a9e0c91e"; sid = "b2e9e0fc-28a1-4d90-ac9e-65d7a9e0c91e"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('FIP 1',
                        'FIP 2',
                        'FIP 3',
                        'FIP 5'); 
                    }  
                    action 'Sense NLG State' : PhysicalFunction  { 
                        @CapellaID { eid = "037e360e-197d-47bf-9ba7-4331e5bbcc98"; sid = "037e360e-197d-47bf-9ba7-4331e5bbcc98"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 5' : FunctionOutputPort  { 
                            @CapellaID { eid = "13e88987-21f7-4935-97a0-cf92c643deb7"; sid = "13e88987-21f7-4935-97a0-cf92c643deb7"; } 
                            attribute :>> isControl = false; 
                            attribute :>> isControlType = false; 
                            attribute :>> kindOfNode = ObjectNodeKind::Unspecified; 
                            attribute :>> ordering = ObjectNodeOrderingKind::FIFO; 
                             
                        }  
                        out port 'FOP 4' : FunctionOutputPort  { 
                            @CapellaID { eid = "8584db70-8e02-4315-bfd4-49478e33bbed"; sid = "8584db70-8e02-4315-bfd4-49478e33bbed"; } 
                            attribute :>> isControl = false; 
                            attribute :>> isControlType = false; 
                            attribute :>> kindOfNode = ObjectNodeKind::Unspecified; 
                            attribute :>> ordering = ObjectNodeOrderingKind::FIFO; 
                             
                        }  
                        out port 'FOP 6' : FunctionOutputPort  { 
                            @CapellaID { eid = "da8382f6-0c6c-483b-aa1f-20a7623c4a9d"; sid = "da8382f6-0c6c-483b-aa1f-20a7623c4a9d"; } 
                            attribute :>> isControl = false; 
                            attribute :>> isControlType = false; 
                            attribute :>> kindOfNode = ObjectNodeKind::Unspecified; 
                            attribute :>> ordering = ObjectNodeOrderingKind::FIFO; 
                             
                        }  
                        out port 'FOP 7' : FunctionOutputPort  { 
                            @CapellaID { eid = "37f81673-c56c-4900-92a7-d1e039852498"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "e4a759c8-054e-4e98-89f9-8f3bba5bd25d"; sid = "e4a759c8-054e-4e98-89f9-8f3bba5bd25d"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "b8bc190c-ef3d-4864-b580-bae454cafc07"; sid = "b8bc190c-ef3d-4864-b580-bae454cafc07"; } 
                            attribute :>> isControl = false; 
                            attribute :>> isControlType = false; 
                            attribute :>> kindOfNode = ObjectNodeKind::Unspecified; 
                            attribute :>> ordering = ObjectNodeOrderingKind::FIFO; 
                             
                        }  
                        in port 'FIP 3' : FunctionInputPort  { 
                            @CapellaID { eid = "148469af-f355-4420-a279-7154a5cacb4d"; sid = "148469af-f355-4420-a279-7154a5cacb4d"; } 
                            attribute :>> isControl = false; 
                            attribute :>> isControlType = false; 
                            attribute :>> kindOfNode = ObjectNodeKind::Unspecified; 
                            attribute :>> ordering = ObjectNodeOrderingKind::FIFO; 
                             
                        }  
                        in port 'FIP 4' : FunctionInputPort  { 
                            @CapellaID { eid = "2ec0e594-6d81-48cc-bc82-563a5cdec73a"; sid = "2ec0e594-6d81-48cc-bc82-563a5cdec73a"; } 
                            attribute :>> isControl = false; 
                            attribute :>> isControlType = false; 
                            attribute :>> kindOfNode = ObjectNodeKind::Unspecified; 
                            attribute :>> ordering = ObjectNodeOrderingKind::FIFO; 
                             
                        }  
                        in port 'FIP 5' : FunctionInputPort  { 
                            @CapellaID { eid = "ed514c87-e8c4-49fc-9e56-74746b8e4621"; sid = "ed514c87-e8c4-49fc-9e56-74746b8e4621"; } 
                            attribute :>> isControl = false; 
                            attribute :>> isControlType = false; 
                            attribute :>> kindOfNode = ObjectNodeKind::Unspecified; 
                            attribute :>> ordering = ObjectNodeOrderingKind::FIFO; 
                             
                        }  
                        in port 'FIP 6' : FunctionInputPort  { 
                            @CapellaID { eid = "507bc0ee-6e9e-4304-aab4-d0e15b174ff5"; sid = "507bc0ee-6e9e-4304-aab4-d0e15b174ff5"; } 
                            attribute :>> isControl = false; 
                            attribute :>> isControlType = false; 
                            attribute :>> kindOfNode = ObjectNodeKind::Unspecified; 
                            attribute :>> ordering = ObjectNodeOrderingKind::FIFO; 
                             
                        }  
                        in port 'FIP 7' : FunctionInputPort  { 
                            @CapellaID { eid = "bb965927-8a61-4084-9f6e-f8b93a02c915"; sid = "bb965927-8a61-4084-9f6e-f8b93a02c915"; } 
                            attribute :>> isControl = false; 
                            attribute :>> isControlType = false; 
                            attribute :>> kindOfNode = ObjectNodeKind::Unspecified; 
                            attribute :>> ordering = ObjectNodeOrderingKind::FIFO; 
                             
                        }  
                        in port 'FIP 8' : FunctionInputPort  { 
                            @CapellaID { eid = "e23a05e8-94b2-4c90-bf6c-71d20b66a728"; sid = "e23a05e8-94b2-4c90-bf6c-71d20b66a728"; } 
                            attribute :>> isControl = false; 
                            attribute :>> isControlType = false; 
                            attribute :>> kindOfNode = ObjectNodeKind::Unspecified; 
                            attribute :>> ordering = ObjectNodeOrderingKind::FIFO; 
                             
                        }  
                        in port 'FIP 9' : FunctionInputPort  { 
                            @CapellaID { eid = "d236b63d-7778-442d-87cc-1286ae5f60ae"; sid = "d236b63d-7778-442d-87cc-1286ae5f60ae"; } 
                            attribute :>> isControl = false; 
                            attribute :>> isControlType = false; 
                            attribute :>> kindOfNode = ObjectNodeKind::Unspecified; 
                            attribute :>> ordering = ObjectNodeOrderingKind::FIFO; 
                             
                        }  
                        in port 'FIP 10' : FunctionInputPort  { 
                            @CapellaID { eid = "8b7552aa-4343-4681-9d35-b207279ca10c"; sid = "8b7552aa-4343-4681-9d35-b207279ca10c"; } 
                            attribute :>> isControl = false; 
                            attribute :>> isControlType = false; 
                            attribute :>> kindOfNode = ObjectNodeKind::Unspecified; 
                            attribute :>> ordering = ObjectNodeOrderingKind::FIFO; 
                             
                        }  
                        in port 'FIP 11' : FunctionInputPort  { 
                            @CapellaID { eid = "ce52c5c3-c39b-4214-ab5e-64200e0ce21f"; sid = "ce52c5c3-c39b-4214-ab5e-64200e0ce21f"; } 
                            attribute :>> isControl = false; 
                            attribute :>> isControlType = false; 
                            attribute :>> kindOfNode = ObjectNodeKind::Unspecified; 
                            attribute :>> ordering = ObjectNodeOrderingKind::FIFO; 
                             
                        }  
                        in port 'FIP 12' : FunctionInputPort  { 
                            @CapellaID { eid = "c71538fe-7ddb-4acf-b3ec-752a34d1a219"; sid = "c71538fe-7ddb-4acf-b3ec-752a34d1a219"; } 
                            attribute :>> isControl = false; 
                            attribute :>> isControlType = false; 
                            attribute :>> kindOfNode = ObjectNodeKind::Unspecified; 
                            attribute :>> ordering = ObjectNodeOrderingKind::FIFO; 
                             
                        }  
                        in port 'FIP 13' : FunctionInputPort  { 
                            @CapellaID { eid = "e5a8154c-327d-494c-8aaa-1bfc4b98cff3"; sid = "e5a8154c-327d-494c-8aaa-1bfc4b98cff3"; } 
                            attribute :>> isControl = false; 
                            attribute :>> isControlType = false; 
                            attribute :>> kindOfNode = ObjectNodeKind::Unspecified; 
                            attribute :>> ordering = ObjectNodeOrderingKind::FIFO; 
                             
                        }  
                        in port 'FIP 16' : FunctionInputPort  { 
                            @CapellaID { eid = "aa3432ee-6ff3-43fa-9384-9410bed3c2af"; sid = "aa3432ee-6ff3-43fa-9384-9410bed3c2af"; } 
                            attribute :>> isControl = false; 
                            attribute :>> isControlType = false; 
                            attribute :>> kindOfNode = ObjectNodeKind::Unspecified; 
                            attribute :>> ordering = ObjectNodeOrderingKind::FIFO; 
                             
                        }  
                        in port 'FIP 18' : FunctionInputPort  { 
                            @CapellaID { eid = "7230f195-f363-4349-8c34-46dc4b66e30a"; sid = "7230f195-f363-4349-8c34-46dc4b66e30a"; } 
                            attribute :>> isControl = false; 
                            attribute :>> isControlType = false; 
                            attribute :>> kindOfNode = ObjectNodeKind::Unspecified; 
                            attribute :>> ordering = ObjectNodeOrderingKind::FIFO; 
                             
                        }  
                        in port 'FIP 14' : FunctionInputPort  { 
                            @CapellaID { eid = "5f8eb61d-19a5-4793-a0ee-d0265d6250f2"; sid = "5f8eb61d-19a5-4793-a0ee-d0265d6250f2"; } 
                            attribute :>> isControl = false; 
                            attribute :>> isControlType = false; 
                            attribute :>> kindOfNode = ObjectNodeKind::Unspecified; 
                            attribute :>> ordering = ObjectNodeOrderingKind::FIFO; 
                             
                        }  
                        in port 'FIP 15' : FunctionInputPort  { 
                            @CapellaID { eid = "c3957605-658b-4515-8b0d-c68e7e3449e8"; sid = "c3957605-658b-4515-8b0d-c68e7e3449e8"; } 
                            attribute :>> isControl = false; 
                            attribute :>> isControlType = false; 
                            attribute :>> kindOfNode = ObjectNodeKind::Unspecified; 
                            attribute :>> ordering = ObjectNodeOrderingKind::FIFO; 
                             
                        }  
                        in port 'FIP 19' : FunctionInputPort  { 
                            @CapellaID { eid = "46c1068a-504f-4b30-be60-ed639e1a7743"; sid = "46c1068a-504f-4b30-be60-ed639e1a7743"; } 
                            attribute :>> isControl = false; 
                            attribute :>> isControlType = false; 
                            attribute :>> kindOfNode = ObjectNodeKind::Unspecified; 
                            attribute :>> ordering = ObjectNodeOrderingKind::FIFO; 
                             
                        }  
                        in port 'FIP 17' : FunctionInputPort  { 
                            @CapellaID { eid = "9b6fddba-1fdf-4691-ae9d-ba0e714d0f3c"; sid = "9b6fddba-1fdf-4691-ae9d-ba0e714d0f3c"; } 
                            attribute :>> isControl = false; 
                            attribute :>> isControlType = false; 
                            attribute :>> kindOfNode = ObjectNodeKind::Unspecified; 
                            attribute :>> ordering = ObjectNodeOrderingKind::FIFO; 
                             
                        }  
                        in port 'FIP 20' : FunctionInputPort  { 
                            @CapellaID { eid = "93ac3f8c-a698-4981-a1c6-6e275158ac56"; sid = "93ac3f8c-a698-4981-a1c6-6e275158ac56"; } 
                            attribute :>> isControl = false; 
                            attribute :>> isControlType = false; 
                            attribute :>> kindOfNode = ObjectNodeKind::Unspecified; 
                            attribute :>> ordering = ObjectNodeOrderingKind::FIFO; 
                             
                        }  
                        in port 'FIP 21' : FunctionInputPort  { 
                            @CapellaID { eid = "be33ecb1-f009-47f2-bd5d-3636eab08786"; } 
                            attribute :>> isControl = false; 
                            attribute :>> isControlType = false; 
                            attribute :>> kindOfNode = ObjectNodeKind::Unspecified; 
                            attribute :>> ordering = ObjectNodeOrderingKind::FIFO; 
                             
                        }  
                        in port 'FIP 22' : FunctionInputPort  { 
                            @CapellaID { eid = "c790f4a4-14f9-4b64-88ce-e78399fbd07e"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 5',
                        'FOP 4',
                        'FOP 6',
                        'FOP 7'); 
                         
                        ref :>> inputs =  ('FIP 1',
                        'FIP 2',
                        'FIP 3',
                        'FIP 4',
                        'FIP 5',
                        'FIP 6',
                        'FIP 7',
                        'FIP 8',
                        'FIP 9',
                        'FIP 10',
                        'FIP 11',
                        'FIP 12',
                        'FIP 13',
                        'FIP 16',
                        'FIP 18',
                        'FIP 14',
                        'FIP 15',
                        'FIP 19',
                        'FIP 17',
                        'FIP 20',
                        'FIP 21',
                        'FIP 22'); 
                    }  
                    action 'Sense Hardware' : PhysicalFunction  { 
                        @CapellaID { eid = "412b273b-51e9-4e0a-864e-e2a6bf9b630c"; sid = "412b273b-51e9-4e0a-864e-e2a6bf9b630c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Sense NLG Uplock Position 1' : PhysicalFunction  { 
                            @CapellaID { eid = "225934eb-0aa0-481d-aa65-b49ec479cb25"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 4' : FunctionOutputPort  { 
                                @CapellaID { eid = "6ba62e75-d766-44f6-a747-230c7481578b"; sid = "6ba62e75-d766-44f6-a747-230c7481578b"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 4'); 
                             
                        }  
                        action 'Sense Shock Position 1' : PhysicalFunction  { 
                            @CapellaID { eid = "dcc2d66c-11c5-4489-999b-44195f8da057"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 7' : FunctionOutputPort  { 
                                @CapellaID { eid = "30f2382a-398f-47e7-a122-3a0337f35cd2"; sid = "30f2382a-398f-47e7-a122-3a0337f35cd2"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 7'); 
                             
                        }  
                        action 'Sense UPLock Position 2' : PhysicalFunction  { 
                            @CapellaID { eid = "acccb0f9-9a33-4df6-a59a-f652f080f6c5"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 5' : FunctionOutputPort  { 
                                @CapellaID { eid = "7136d569-b12a-490f-84fe-0d4df033e826"; sid = "7136d569-b12a-490f-84fe-0d4df033e826"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 5'); 
                             
                        }  
                        action 'Sense Shock Position 2' : PhysicalFunction  { 
                            @CapellaID { eid = "d9f11822-2039-40f2-9db6-9f4540f891f4"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 6' : FunctionOutputPort  { 
                                @CapellaID { eid = "b899193d-da3b-4e0a-abd7-98b112bdc0a8"; sid = "b899193d-da3b-4e0a-abd7-98b112bdc0a8"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 6'); 
                             
                        }  
                        action 'Sense DWNLock Position 2' : PhysicalFunction  { 
                            @CapellaID { eid = "a2be5c44-af82-45cf-b957-34cd08956596"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 3' : FunctionOutputPort  { 
                                @CapellaID { eid = "82e5ffa1-bb5b-42df-94ce-fab5df6fc4dd"; sid = "82e5ffa1-bb5b-42df-94ce-fab5df6fc4dd"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 3'); 
                             
                        }  
                        action 'Sense DWNLock Position 1' : PhysicalFunction  { 
                            @CapellaID { eid = "a4f3c54a-f412-4fb4-ac36-c6edbe69602b"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 2' : FunctionOutputPort  { 
                                @CapellaID { eid = "281456cf-9d1e-4f2a-b8d4-a099d6615068"; sid = "281456cf-9d1e-4f2a-b8d4-a099d6615068"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 2'); 
                             
                        }  
                        action 'Sense NLG Door Position' : PhysicalFunction  { 
                            @CapellaID { eid = "01a64179-df9e-4bf0-81d2-c50d65812c4e"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "575edf1e-3412-4844-8805-36c52bb70e36"; sid = "575edf1e-3412-4844-8805-36c52bb70e36"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 1'); 
                             
                        }  
                        ref :>> ownedFunctions =  ('Sense NLG Uplock Position 1',
                        'Sense Shock Position 1',
                        'Sense UPLock Position 2',
                        'Sense Shock Position 2',
                        'Sense DWNLock Position 2',
                        'Sense DWNLock Position 1',
                        'Sense NLG Door Position'); 
                         
                    }  
                    action 'Tranmit' : PhysicalFunction  { 
                        @CapellaID { eid = "d40c7efd-d95a-4974-b493-25c8b095d25a"; sid = "d40c7efd-d95a-4974-b493-25c8b095d25a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 2' : FunctionOutputPort  { 
                            @CapellaID { eid = "6ce4cdf1-44c4-466d-8a3d-dfc8fd087ff7"; sid = "6ce4cdf1-44c4-466d-8a3d-dfc8fd087ff7"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "92351843-301c-4ca8-ab0a-1afc9cc01dd4"; sid = "92351843-301c-4ca8-ab0a-1afc9cc01dd4"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 2'); 
                         
                        ref :>> inputs =  ('FIP 1'); 
                    }  
                    action 'Transmit Ground Force' : PhysicalFunction  { 
                        @CapellaID { eid = "8ce74bd9-6d43-42ac-b1e6-34c213241ad5"; sid = "8ce74bd9-6d43-42ac-b1e6-34c213241ad5"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "e21aae30-69f0-4955-8e94-35d8dcf24591"; sid = "e21aae30-69f0-4955-8e94-35d8dcf24591"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "3435add8-675c-4457-b361-d69d859fea09"; sid = "3435add8-675c-4457-b361-d69d859fea09"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Transmit NLG Forces' : PhysicalFunction  { 
                        @CapellaID { eid = "a25a3faf-7b23-4441-983c-9a9548c77246"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Dampen Spring' : PhysicalFunction  { 
                            @CapellaID { eid = "f81a5d32-5876-40ea-bb09-66dcbdae8afd"; sid = "f81a5d32-5876-40ea-bb09-66dcbdae8afd"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "e0c0467c-26d6-4a9a-b5e5-8e41e071b4a8"; sid = "e0c0467c-26d6-4a9a-b5e5-8e41e071b4a8"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "e859f015-6a32-45f9-9649-af0018959fcc"; sid = "e859f015-6a32-45f9-9649-af0018959fcc"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 1'); 
                             
                            ref :>> inputs =  ('FIP 1'); 
                        }  
                        action 'Transmit NLG Structural Post' : PhysicalFunction  { 
                            @CapellaID { eid = "04381d02-10b5-4816-b56d-5859064b3a06"; sid = "04381d02-10b5-4816-b56d-5859064b3a06"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 3' : FunctionOutputPort  { 
                                @CapellaID { eid = "0111c000-6523-459d-a868-421524735de9"; } 
                                attribute :>> isControl = false; 
                                attribute :>> isControlType = false; 
                                attribute :>> kindOfNode = ObjectNodeKind::Unspecified; 
                                attribute :>> ordering = ObjectNodeOrderingKind::FIFO; 
                                 
                            }  
                            out port 'FOP 1' : FunctionOutputPort  { 
                                @CapellaID { eid = "ed622ad1-b288-49e5-9ad6-d87b38b52f39"; sid = "ed622ad1-b288-49e5-9ad6-d87b38b52f39"; } 
                                attribute :>> isControl = false; 
                                attribute :>> isControlType = false; 
                                attribute :>> kindOfNode = ObjectNodeKind::Unspecified; 
                                attribute :>> ordering = ObjectNodeOrderingKind::FIFO; 
                                 
                            }  
                            out port 'FOP 6' : FunctionOutputPort  { 
                                @CapellaID { eid = "4387b0fc-903a-40b2-a651-97730beb2cb7"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "091512a3-7319-4af6-a717-536ffbad78b2"; sid = "091512a3-7319-4af6-a717-536ffbad78b2"; } 
                                attribute :>> isControl = false; 
                                attribute :>> isControlType = false; 
                                attribute :>> kindOfNode = ObjectNodeKind::Unspecified; 
                                attribute :>> ordering = ObjectNodeOrderingKind::FIFO; 
                                 
                            }  
                            in port 'FIP 2' : FunctionInputPort  { 
                                @CapellaID { eid = "3ac42a7f-778b-4e18-b3b4-3d345e9fde9d"; sid = "3ac42a7f-778b-4e18-b3b4-3d345e9fde9d"; } 
                                attribute :>> isControl = false; 
                                attribute :>> isControlType = false; 
                                attribute :>> kindOfNode = ObjectNodeKind::Unspecified; 
                                attribute :>> ordering = ObjectNodeOrderingKind::FIFO; 
                                 
                            }  
                            in port 'FIP 3' : FunctionInputPort  { 
                                @CapellaID { eid = "00894f97-6948-47ff-acac-4015c0001676"; sid = "00894f97-6948-47ff-acac-4015c0001676"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 3',
                            'FOP 1',
                            'FOP 6'); 
                             
                            ref :>> inputs =  ('FIP 1',
                            'FIP 2',
                            'FIP 3'); 
                        }  
                        interface '80b3ef0e-d505-453d-837d-9da01e94fde7' : FunctionalExchange 
                            connect source ::> 'Dampen Spring'.'FOP 1'
                            to target ::> 'Transmit NLG Structural Post'.'FIP 1' { 
                            @CapellaID { eid = "80b3ef0e-d505-453d-837d-9da01e94fde7"; sid = "80b3ef0e-d505-453d-837d-9da01e94fde7"; } 
                            attribute :>> isMulticast = false; 
                            attribute :>> isMultireceive = false; 
                            attribute :>> kindOfRate = RateKind::Unspecified; 
                            attribute :>> interfaceName = "Taxi and Landing Loads"; 
                             
                        }  
                        ref :>> ownedFunctions =  ('Dampen Spring',
                        'Transmit NLG Structural Post'); 
                         
                        ref :>> ownedFunctionalExchanges =  ('80b3ef0e-d505-453d-837d-9da01e94fde7'); 
                    }  
                    action 'Support LG' : PhysicalFunction  { 
                        @CapellaID { eid = "10680770-dc89-4678-afbb-314c5227dec0"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Support LMLG ' : PhysicalFunction  { 
                            @CapellaID { eid = "82bf0831-df34-4403-88a3-55b8f0e896d0"; sid = "82bf0831-df34-4403-88a3-55b8f0e896d0"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "a944e330-ee71-4889-ae21-4992e6f95e8f"; } 
                                attribute :>> isControl = false; 
                                attribute :>> isControlType = false; 
                                attribute :>> kindOfNode = ObjectNodeKind::Unspecified; 
                                attribute :>> ordering = ObjectNodeOrderingKind::FIFO; 
                                 
                            }  
                            out port 'FOP 2' : FunctionOutputPort  { 
                                @CapellaID { eid = "15dad3c0-1277-4666-a1cb-eabb956fb564"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "fb6d7023-c0c2-4b77-b3e2-b749f695b140"; sid = "fb6d7023-c0c2-4b77-b3e2-b749f695b140"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 1',
                            'FOP 2'); 
                             
                            ref :>> inputs =  ('FIP 1'); 
                        }  
                        action 'Support RMLG' : PhysicalFunction  { 
                            @CapellaID { eid = "2277e194-bb09-4985-b685-c47a65737e58"; sid = "2277e194-bb09-4985-b685-c47a65737e58"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "227bf9b4-23a7-4c3c-8ce8-8aa29bac9466"; } 
                                attribute :>> isControl = false; 
                                attribute :>> isControlType = false; 
                                attribute :>> kindOfNode = ObjectNodeKind::Unspecified; 
                                attribute :>> ordering = ObjectNodeOrderingKind::FIFO; 
                                 
                            }  
                            out port 'FOP 2' : FunctionOutputPort  { 
                                @CapellaID { eid = "5c31e804-87de-47bf-b90f-0e011c20ce42"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "4f3a9fb9-72b5-440a-8e8b-78f28f6db749"; sid = "4f3a9fb9-72b5-440a-8e8b-78f28f6db749"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 1',
                            'FOP 2'); 
                             
                            ref :>> inputs =  ('FIP 1'); 
                        }  
                        action 'Duplicate 4' : PhysicalFunction  { 
                            @CapellaID { eid = "8d86aa32-a683-4654-99bd-6642f2c922e9"; sid = "8d86aa32-a683-4654-99bd-6642f2c922e9"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::DUPLICATE; 
                            attribute :>> isMaxInclusive = false; 
                            attribute :>> isMinInclusive = false; 
                            attribute :>> isOrdered = false; 
                            attribute :>> isUnique = false; 
                            out port 'FOP 2' : FunctionOutputPort  { 
                                @CapellaID { eid = "becc7c40-ed49-4544-9bc1-ee2eedf09287"; sid = "becc7c40-ed49-4544-9bc1-ee2eedf09287"; } 
                                attribute :>> isControl = false; 
                                attribute :>> isControlType = false; 
                                attribute :>> kindOfNode = ObjectNodeKind::Unspecified; 
                                attribute :>> ordering = ObjectNodeOrderingKind::FIFO; 
                                 
                            }  
                            out port 'FOP 3' : FunctionOutputPort  { 
                                @CapellaID { eid = "259b6445-3f6c-4c32-bb7e-fa06f7524a96"; sid = "259b6445-3f6c-4c32-bb7e-fa06f7524a96"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "ef63c14d-db92-419b-ad73-c106c8237400"; sid = "ef63c14d-db92-419b-ad73-c106c8237400"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 2',
                            'FOP 3'); 
                             
                            ref :>> inputs =  ('FIP 1'); 
                        }  
                        action 'Gather 5' : PhysicalFunction  { 
                            @CapellaID { eid = "fcb53eb2-625f-4018-9a0f-00491710850c"; sid = "fcb53eb2-625f-4018-9a0f-00491710850c"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::GATHER; 
                            attribute :>> isMaxInclusive = false; 
                            attribute :>> isMinInclusive = false; 
                            attribute :>> isOrdered = false; 
                            attribute :>> isUnique = false; 
                            out port 'FOP 4' : FunctionOutputPort  { 
                                @CapellaID { eid = "5b422142-9ad7-43da-9950-0d5302adea01"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "67c2e4d2-a2b8-4a52-96fd-c92c2c3ce556"; sid = "67c2e4d2-a2b8-4a52-96fd-c92c2c3ce556"; } 
                                attribute :>> isControl = false; 
                                attribute :>> isControlType = false; 
                                attribute :>> kindOfNode = ObjectNodeKind::Unspecified; 
                                attribute :>> ordering = ObjectNodeOrderingKind::FIFO; 
                                 
                            }  
                            in port 'FIP 2' : FunctionInputPort  { 
                                @CapellaID { eid = "ee689794-e190-444e-a8e4-aeeab9c1e843"; } 
                                attribute :>> isControl = false; 
                                attribute :>> isControlType = false; 
                                attribute :>> kindOfNode = ObjectNodeKind::Unspecified; 
                                attribute :>> ordering = ObjectNodeOrderingKind::FIFO; 
                                 
                            }  
                            in port 'FIP 3' : FunctionInputPort  { 
                                @CapellaID { eid = "a7ed090d-be82-4d47-a55b-4f671242678b"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 4'); 
                             
                            ref :>> inputs =  ('FIP 1',
                            'FIP 2',
                            'FIP 3'); 
                        }  
                        action 'Gather 6' : PhysicalFunction  { 
                            @CapellaID { eid = "b5ccb76c-f28d-49d9-868b-998379a91397"; sid = "b5ccb76c-f28d-49d9-868b-998379a91397"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::GATHER; 
                            attribute :>> isMaxInclusive = false; 
                            attribute :>> isMinInclusive = false; 
                            attribute :>> isOrdered = false; 
                            attribute :>> isUnique = false; 
                            out port 'FOP 1' : FunctionOutputPort  { 
                                @CapellaID { eid = "a605b576-21a8-4b10-8f94-3107809fa0ad"; } 
                                attribute :>> isControl = false; 
                                attribute :>> isControlType = false; 
                                attribute :>> kindOfNode = ObjectNodeKind::Unspecified; 
                                attribute :>> ordering = ObjectNodeOrderingKind::FIFO; 
                                 
                            }  
                            in port 'FIP 2' : FunctionInputPort  { 
                                @CapellaID { eid = "f009f9c2-eafd-4b07-aec8-2e88cad93360"; } 
                                attribute :>> isControl = false; 
                                attribute :>> isControlType = false; 
                                attribute :>> kindOfNode = ObjectNodeKind::Unspecified; 
                                attribute :>> ordering = ObjectNodeOrderingKind::FIFO; 
                                 
                            }  
                            in port 'FIP 3' : FunctionInputPort  { 
                                @CapellaID { eid = "400be0e9-cba5-4b06-9c78-c4094fd23420"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('FOP 1'); 
                             
                            ref :>> inputs =  ('FIP 2',
                            'FIP 3'); 
                        }  
                        interface 'c875708e-d2a8-4339-a68e-6caa3710a3b2' : FunctionalExchange 
                            connect source ::> 'Duplicate 4'.'FOP 2'
                            to target ::> 'Support LMLG '.'FIP 1' { 
                            @CapellaID { eid = "c875708e-d2a8-4339-a68e-6caa3710a3b2"; sid = "c875708e-d2a8-4339-a68e-6caa3710a3b2"; } 
                            attribute :>> isMulticast = false; 
                            attribute :>> isMultireceive = false; 
                            attribute :>> kindOfRate = RateKind::Unspecified; 
                            attribute :>> interfaceName = "Structural"; 
                             
                        }  
                        interface 'e7c314a6-3c21-479d-aa71-66425a33cfa8' : FunctionalExchange 
                            connect source ::> 'Duplicate 4'.'FOP 3'
                            to target ::> 'Support RMLG'.'FIP 1' { 
                            @CapellaID { eid = "e7c314a6-3c21-479d-aa71-66425a33cfa8"; sid = "e7c314a6-3c21-479d-aa71-66425a33cfa8"; } 
                            attribute :>> isMulticast = false; 
                            attribute :>> isMultireceive = false; 
                            attribute :>> kindOfRate = RateKind::Unspecified; 
                            attribute :>> interfaceName = "Structural"; 
                             
                        }  
                        interface '8a8467fc-a22f-40e6-851e-a9a054da3c1a' : FunctionalExchange 
                            connect source ::> 'Support LMLG '.'FOP 1'
                            to target ::> 'Gather 5'.'FIP 2' { 
                            @CapellaID { eid = "8a8467fc-a22f-40e6-851e-a9a054da3c1a"; } 
                            attribute :>> isMulticast = false; 
                            attribute :>> isMultireceive = false; 
                            attribute :>> kindOfRate = RateKind::Unspecified; 
                            attribute :>> interfaceName = "Structural"; 
                             
                        }  
                        interface '13b62c11-2e85-429d-bf33-34a9562db7af' : FunctionalExchange 
                            connect source ::> 'Support RMLG'.'FOP 1'
                            to target ::> 'Gather 5'.'FIP 3' { 
                            @CapellaID { eid = "13b62c11-2e85-429d-bf33-34a9562db7af"; } 
                            attribute :>> isMulticast = false; 
                            attribute :>> isMultireceive = false; 
                            attribute :>> kindOfRate = RateKind::Unspecified; 
                            attribute :>> interfaceName = "Structural"; 
                             
                        }  
                        interface 'c7cd4cdf-23d8-45f2-9fc2-13c3399a7a5e' : FunctionalExchange 
                            connect source ::> 'Support LMLG '.'FOP 2'
                            to target ::> 'Gather 6'.'FIP 2' { 
                            @CapellaID { eid = "c7cd4cdf-23d8-45f2-9fc2-13c3399a7a5e"; } 
                            attribute :>> isMulticast = false; 
                            attribute :>> isMultireceive = false; 
                            attribute :>> kindOfRate = RateKind::Unspecified; 
                            attribute :>> interfaceName = "Structural"; 
                             
                        }  
                        interface 'e6e12085-825a-45ad-81cf-1c436a1a0cee' : FunctionalExchange 
                            connect source ::> 'Support RMLG'.'FOP 2'
                            to target ::> 'Gather 6'.'FIP 3' { 
                            @CapellaID { eid = "e6e12085-825a-45ad-81cf-1c436a1a0cee"; } 
                            attribute :>> isMulticast = false; 
                            attribute :>> isMultireceive = false; 
                            attribute :>> kindOfRate = RateKind::Unspecified; 
                            attribute :>> interfaceName = "Structural"; 
                             
                        }  
                        ref :>> ownedFunctions =  ('Support LMLG ',
                        'Support RMLG',
                        'Duplicate 4',
                        'Gather 5',
                        'Gather 6'); 
                         
                        ref :>> ownedFunctionalExchanges =  ('c875708e-d2a8-4339-a68e-6caa3710a3b2',
                        'e7c314a6-3c21-479d-aa71-66425a33cfa8',
                        '8a8467fc-a22f-40e6-851e-a9a054da3c1a',
                        '13b62c11-2e85-429d-bf33-34a9562db7af',
                        'c7cd4cdf-23d8-45f2-9fc2-13c3399a7a5e',
                        'e6e12085-825a-45ad-81cf-1c436a1a0cee'); 
                    }  
                    action 'Supply Pressure' : PhysicalFunction  { 
                        @CapellaID { eid = "5d3b4957-39ce-4fef-942f-d1b57b4a9788"; sid = "5d3b4957-39ce-4fef-942f-d1b57b4a9788"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "a3b4dd61-c8e2-4f83-aa43-814600582bc5"; sid = "a3b4dd61-c8e2-4f83-aa43-814600582bc5"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "5500a8ec-949c-465f-a560-a9eac14052fe"; } 
                            attribute :>> isControl = false; 
                            attribute :>> isControlType = false; 
                            attribute :>> kindOfNode = ObjectNodeKind::Unspecified; 
                            attribute :>> ordering = ObjectNodeOrderingKind::FIFO; 
                             
                        }  
                        out port 'FOP 3' : FunctionOutputPort  { 
                            @CapellaID { eid = "bf17d9d4-25ae-4efb-9fe5-6bb528d48373"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "35434a1b-e829-4d79-9851-fd7ab4c34cae"; sid = "35434a1b-e829-4d79-9851-fd7ab4c34cae"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "3ddf8b51-afeb-477f-b9c5-0f7d177c4144"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2',
                        'FOP 3'); 
                         
                        ref :>> inputs =  ('FIP 1',
                        'FIP 2'); 
                    }  
                    action 'SupplyPressur' : PhysicalFunction  { 
                        @CapellaID { eid = "d47e2d82-3f36-4c21-b7fa-d7b6edc00fcb"; sid = "d47e2d82-3f36-4c21-b7fa-d7b6edc00fcb"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "70d0bb08-38b0-4c85-87c1-de768b3b58a7"; sid = "70d0bb08-38b0-4c85-87c1-de768b3b58a7"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "028eeea6-9a8e-4224-ab70-42907659a8e5"; sid = "028eeea6-9a8e-4224-ab70-42907659a8e5"; } 
                            attribute :>> isControl = false; 
                            attribute :>> isControlType = false; 
                            attribute :>> kindOfNode = ObjectNodeKind::Unspecified; 
                            attribute :>> ordering = ObjectNodeOrderingKind::FIFO; 
                             
                        }  
                        out port 'FOP 3' : FunctionOutputPort  { 
                            @CapellaID { eid = "569f77e1-7f18-4656-9b3e-95c5da84bb9d"; sid = "569f77e1-7f18-4656-9b3e-95c5da84bb9d"; } 
                            attribute :>> isControl = false; 
                            attribute :>> isControlType = false; 
                            attribute :>> kindOfNode = ObjectNodeKind::Unspecified; 
                            attribute :>> ordering = ObjectNodeOrderingKind::FIFO; 
                             
                        }  
                        out port 'FOP 4' : FunctionOutputPort  { 
                            @CapellaID { eid = "f7f5c4ab-1c2c-43a6-9ec6-309ce5ec0700"; sid = "f7f5c4ab-1c2c-43a6-9ec6-309ce5ec0700"; } 
                            attribute :>> isControl = false; 
                            attribute :>> isControlType = false; 
                            attribute :>> kindOfNode = ObjectNodeKind::Unspecified; 
                            attribute :>> ordering = ObjectNodeOrderingKind::FIFO; 
                             
                        }  
                        out port 'FOP 5' : FunctionOutputPort  { 
                            @CapellaID { eid = "81d482a8-8760-4622-b763-5b3aea39e4fb"; sid = "81d482a8-8760-4622-b763-5b3aea39e4fb"; } 
                            attribute :>> isControl = false; 
                            attribute :>> isControlType = false; 
                            attribute :>> kindOfNode = ObjectNodeKind::Unspecified; 
                            attribute :>> ordering = ObjectNodeOrderingKind::FIFO; 
                             
                        }  
                        out port 'FOP 6' : FunctionOutputPort  { 
                            @CapellaID { eid = "3fc86962-8b89-4ce8-9d93-2ca7968b262d"; sid = "3fc86962-8b89-4ce8-9d93-2ca7968b262d"; } 
                            attribute :>> isControl = false; 
                            attribute :>> isControlType = false; 
                            attribute :>> kindOfNode = ObjectNodeKind::Unspecified; 
                            attribute :>> ordering = ObjectNodeOrderingKind::FIFO; 
                             
                        }  
                        out port 'FOP 8' : FunctionOutputPort  { 
                            @CapellaID { eid = "bf89528d-88a0-40fa-8dc4-b83f07d99f84"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "bbbcbb8e-94bd-4cfa-898b-2cde21d4e9b1"; sid = "bbbcbb8e-94bd-4cfa-898b-2cde21d4e9b1"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "08d0d338-ed5b-46ad-a5f9-79e865595dd1"; sid = "08d0d338-ed5b-46ad-a5f9-79e865595dd1"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2',
                        'FOP 3',
                        'FOP 4',
                        'FOP 5',
                        'FOP 6',
                        'FOP 8'); 
                         
                        ref :>> inputs =  ('FIP 1',
                        'FIP 2'); 
                    }  
                    action 'Duplicate 67' : PhysicalFunction  { 
                        @CapellaID { eid = "47ec4276-7de2-4e97-9f14-272d81cc3764"; sid = "47ec4276-7de2-4e97-9f14-272d81cc3764"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::DUPLICATE; 
                        attribute :>> isMaxInclusive = false; 
                        attribute :>> isMinInclusive = false; 
                        attribute :>> isOrdered = false; 
                        attribute :>> isUnique = false; 
                        out port 'FOP 1' : FunctionOutputPort  { 
                            @CapellaID { eid = "d41467a9-b160-4aeb-b609-4803c117648a"; sid = "d41467a9-b160-4aeb-b609-4803c117648a"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "16c9af5a-b6eb-4495-9118-74c644e32092"; sid = "16c9af5a-b6eb-4495-9118-74c644e32092"; } 
                            attribute :>> isControl = false; 
                            attribute :>> isControlType = false; 
                            attribute :>> kindOfNode = ObjectNodeKind::Unspecified; 
                            attribute :>> ordering = ObjectNodeOrderingKind::FIFO; 
                             
                        }  
                        out port 'FOP 3' : FunctionOutputPort  { 
                            @CapellaID { eid = "5fb645df-e9a6-483e-ae6f-52eea6cde03b"; sid = "5fb645df-e9a6-483e-ae6f-52eea6cde03b"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "ad0c58c6-f4c7-4122-8970-1cef7c642e56"; sid = "ad0c58c6-f4c7-4122-8970-1cef7c642e56"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2',
                        'FOP 3'); 
                         
                        ref :>> inputs =  ('FIP 1'); 
                    }  
                    action 'ActuateLMLG' : PhysicalFunction  { 
                        @CapellaID { eid = "12b46572-6448-427c-bbb4-977a23fd3468"; sid = "12b46572-6448-427c-bbb4-977a23fd3468"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "d0a86217-9d18-4c26-976d-a5f86a2c8895"; sid = "d0a86217-9d18-4c26-976d-a5f86a2c8895"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "005b4c19-4cca-464e-a918-be7fc55bc339"; sid = "005b4c19-4cca-464e-a918-be7fc55bc339"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('FIP 1',
                        'FIP 2'); 
                    }  
                    action 'Actuate RMLG' : PhysicalFunction  { 
                        @CapellaID { eid = "049fee86-f4ff-48e9-978e-ef38bb5b12da"; sid = "049fee86-f4ff-48e9-978e-ef38bb5b12da"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "6146f8ad-c5b3-491d-9b05-2c4f303b857b"; sid = "6146f8ad-c5b3-491d-9b05-2c4f303b857b"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "92578c4c-2966-4d8a-8088-30784627e4cf"; sid = "92578c4c-2966-4d8a-8088-30784627e4cf"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('FIP 1',
                        'FIP 2'); 
                    }  
                    action 'Channel' : PhysicalFunction  { 
                        @CapellaID { eid = "bed4009f-981f-412f-ba31-e8121146e5e0"; sid = "bed4009f-981f-412f-ba31-e8121146e5e0"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "c5c9a591-8991-43b5-a0f5-0edbed05ecfd"; sid = "c5c9a591-8991-43b5-a0f5-0edbed05ecfd"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "071f30d8-9a89-446c-850d-684519ed7e4c"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "23b04c67-a365-4b7e-bffd-bdaf4d40d203"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1',
                        'FIP 2'); 
                    }  
                    action 'Maintain Pressure' : PhysicalFunction  { 
                        @CapellaID { eid = "0ee28067-e497-4f66-9328-d4670f46cf67"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "3eccb699-43ea-4201-8cdc-89a8fdb9f094"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "830d5c86-f913-4e9d-b432-d6c546a06904"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Store' : PhysicalFunction  { 
                        @CapellaID { eid = "78b548d9-5864-4ffc-bb31-11beacf16ace"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "05e871e5-bec0-4242-96e3-9a95d984c13e"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "e905b601-6a9e-489e-921d-9c4dac1ff107"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "8cb5d0b5-7d95-4eae-800d-cc2088ef4a67"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2'); 
                         
                        ref :>> inputs =  ('FIP 1'); 
                    }  
                    action 'Pump Fluid' : PhysicalFunction  { 
                        @CapellaID { eid = "63e0ef9a-41db-475a-b061-db4e3f874278"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "5ca6afe7-7e81-4f0f-8599-231be8fc504f"; } 
                            attribute :>> isControl = false; 
                            attribute :>> isControlType = false; 
                            attribute :>> kindOfNode = ObjectNodeKind::Unspecified; 
                            attribute :>> ordering = ObjectNodeOrderingKind::FIFO; 
                             
                        }  
                        in port 'Fluid' : FunctionInputPort  { 
                            @CapellaID { eid = "3c32054a-069c-4803-a966-bac0e14e9eeb"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('Fluid'); 
                    }  
                    action 'Control' : PhysicalFunction  { 
                        @CapellaID { eid = "5ceeb92e-a6d0-48f8-a8c1-020d4ece2cd0"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "a099fff5-1a4a-40ab-b222-6438f6baceab"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "7d13f400-c2ce-4427-acf2-ba3227b09482"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "d194aa71-a9fa-4a9b-9a50-5859d25879d8"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1',
                        'FIP 2'); 
                    }  
                    action 'Pump Fliud' : PhysicalFunction  { 
                        @CapellaID { eid = "243ea064-6974-4f15-b150-023833d686e1"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "212056e0-a69e-462d-9a34-543c8b69c0c6"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "80de3b2f-3914-41bd-8840-2053b2e4c26c"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Regulate' : PhysicalFunction  { 
                        @CapellaID { eid = "d7360c2f-f158-4ac9-9f83-b720825a09c6"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "18a3dc31-3a82-45b3-b036-f62b7c8a85cc"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "279eea02-7db3-4f45-92d0-d12cae019e04"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "b280a5c0-671f-42de-8c57-d6650a728774"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1',
                        'FIP 2'); 
                    }  
                    action 'Isolate ' : PhysicalFunction  { 
                        @CapellaID { eid = "86e861ee-a227-48e3-b36f-86754411a984"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "0a5f4d9e-4a48-4527-b6d0-e30053565eb8"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "785017ed-111c-4174-a4d4-c7fd08017bf0"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "cbecb96e-8fe8-426b-a3f0-a46c5f870b96"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1',
                        'FIP 2'); 
                    }  
                    action 'Slow Rotation' : PhysicalFunction  { 
                        @CapellaID { eid = "e7da06bd-fc01-459c-8c9f-0b0bc77a8a04"; sid = "e7da06bd-fc01-459c-8c9f-0b0bc77a8a04"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "66f7c3d4-ed97-4478-855c-d387b8d0b456"; sid = "66f7c3d4-ed97-4478-855c-d387b8d0b456"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "396be078-d1af-490c-a9a6-45a6ac92d0c6"; sid = "396be078-d1af-490c-a9a6-45a6ac92d0c6"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Sense Weight on Wheels' : PhysicalFunction  { 
                        @CapellaID { eid = "1e8cb6d0-01df-4a69-983a-34abb3da5b55"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "ccc9b8fb-792d-4ebb-bf55-fe78b2dcca17"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                    }  
                    action 'Sense Weight on Wheels 2' : PhysicalFunction  { 
                        @CapellaID { eid = "e8335578-2d3f-4548-aa85-84a018c42fde"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "fb3c1355-1636-490e-9cc2-2e21cba986aa"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                    }  
                    action 'Provide Spring Support' : PhysicalFunction  { 
                        @CapellaID { eid = "4ff7d402-5ff3-4ed0-8653-6fd6691fb8a8"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "67e1518f-0f18-4a3e-988f-97e28b97ab01"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "e7b78ebb-4569-4b17-92ea-3aaf7c1e0c97"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Manage NLG' : PhysicalFunction  { 
                        @CapellaID { eid = "53f77006-ee24-4830-9da9-0fac1628588d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "848d4e6a-9204-4c12-b17a-11d637d40f84"; sid = "848d4e6a-9204-4c12-b17a-11d637d40f84"; } 
                            attribute :>> isControl = false; 
                            attribute :>> isControlType = false; 
                            attribute :>> kindOfNode = ObjectNodeKind::Unspecified; 
                            attribute :>> ordering = ObjectNodeOrderingKind::FIFO; 
                             
                        }  
                        in port 'FIP 3' : FunctionInputPort  { 
                            @CapellaID { eid = "a0f3a4cd-abdf-4e76-9ea7-0c1b2dc7b644"; sid = "a0f3a4cd-abdf-4e76-9ea7-0c1b2dc7b644"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 3'); 
                    }  
                    action 'Store H Fluid' : PhysicalFunction  { 
                        @CapellaID { eid = "fe6fc702-3d57-421b-b1ea-2c865066175b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "7b9873c9-6dd3-4441-b6b1-04a4d59db710"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "c36e7676-182f-4141-a0ed-484abf23dfea"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "f85f98aa-7a59-46c6-835d-9f512a940444"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "f1e75676-1702-480e-a605-77823726f38d"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2'); 
                         
                        ref :>> inputs =  ('FIP 1',
                        'FIP 2'); 
                    }  
                    action 'Release Selector Valve Pressure' : PhysicalFunction  { 
                        @CapellaID { eid = "9b20390b-1aa6-41ce-8a24-4fb2eb63bffa"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "afaac39e-d022-4e8c-958d-143dc8edb2f5"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "5ec1cec2-e89a-454e-80c6-f58ed1692773"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "371b969e-6c8b-4b07-bccb-950b35c03370"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1',
                        'FIP 2'); 
                    }  
                    action 'Release Door Valve Pressure ' : PhysicalFunction  { 
                        @CapellaID { eid = "7bc51ecc-fbb6-4aea-a50b-3bdb7aaa076d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "e5cd368d-583b-402a-9ddd-23f4b13a8555"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "589fba8f-7086-4efa-a9c0-79c23d53c105"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "548bf2aa-69ff-4372-9f8a-0c2442b7e5e3"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1',
                        'FIP 2'); 
                    }  
                    action 'Control Pressure' : PhysicalFunction  { 
                        @CapellaID { eid = "88a856dd-e376-471f-a34f-754e15462f66"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "8922b56e-0031-45ca-8b1d-2f1aa666d922"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "2096f8aa-4dec-4e79-8369-b2cc36bc7707"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "a7b044b8-8d81-42eb-bac1-b712676f413d"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "c6c4d870-58e8-4608-a6fc-bd55c1e861ae"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1',
                        'FOP 2'); 
                         
                        ref :>> inputs =  ('FIP 1',
                        'FIP 2'); 
                    }  
                    action 'Move Door' : PhysicalFunction  { 
                        @CapellaID { eid = "134988bc-c5f3-442c-8dba-fe5850eb5604"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "587f7102-b705-44f9-b6e8-7688ddf3e769"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "dd4ba36c-2390-489b-94a8-2acc513a3074"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Open and Close' : PhysicalFunction  { 
                        @CapellaID { eid = "aa71f57e-a08c-4396-958c-34d4406c7ef2"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "a945cf87-adbb-49a6-8d96-39ebd0718ad7"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "187f6feb-7887-4949-8311-324435de5f27"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('FIP 1',
                        'FIP 2'); 
                    }  
                    action 'Manage NLG Door' : PhysicalFunction  { 
                        @CapellaID { eid = "c984a5f8-c23e-485b-b0ac-e5f42ab9d070"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "68892456-1e5c-4145-ae6e-00bf4f117a5a"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "b24fa406-cbb5-413d-a160-36cb22a2ea12"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'NLG Dump' : PhysicalFunction  { 
                        @CapellaID { eid = "8af18b59-b94b-4a24-8cd2-05d70ab9462a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "7d3cc561-96bd-4169-a5d0-cf490a6a5216"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "54c14ac7-cdc4-4885-866c-66d8e5513a06"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'NLG Door Dump' : PhysicalFunction  { 
                        @CapellaID { eid = "0bc9eedc-c48d-4879-a5d0-dacdc38ba662"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "b5fb69c2-1b1d-4b1c-83f9-70ee5a17ab7a"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "bec503d3-1a56-45dc-84b3-4bf92671c712"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                        ref :>> inputs =  ('FIP 1'); 
                    }  
                    action 'Control Gear' : PhysicalFunction  { 
                        @CapellaID { eid = "86834917-fd54-48f5-819d-fc24ed772bfd"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "1281bafe-9530-4ac2-b16d-e8f69a36ceac"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                    }  
                    action 'NLG Gear Override' : PhysicalFunction  { 
                        @CapellaID { eid = "5bd4d8dd-f89a-455e-8830-3b42845157e3"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "dd9896dd-af41-41f5-b4ca-5cae9433f078"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                    }  
                    action 'NLG Door Overide' : PhysicalFunction  { 
                        @CapellaID { eid = "d340eb48-1f26-4fa8-aaad-9ca1f7487ab6"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "96924a55-ca87-4d32-b767-abee6834c2ec"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('FOP 1'); 
                         
                    }  
                    interface '0dec75ca-92e1-492c-b25d-fa132c5454c2' : FunctionalExchange 
                        connect source ::> 'Initiate Mission'.'outInteraction 19'
                        to target ::> 'Scan'.'inInteraction 19' { 
                        @CapellaID { eid = "0dec75ca-92e1-492c-b25d-fa132c5454c2"; sid = "0dec75ca-92e1-492c-b25d-fa132c5454c2"; } 
                        attribute :>> isMulticast = false; 
                        attribute :>> isMultireceive = false; 
                        attribute :>> kindOfRate = RateKind::Unspecified; 
                        attribute :>> interfaceName = "Interaction 19"; 
                         
                    }  
                    interface '93290df8-fed9-49d1-beed-b9aaf7a44f24' : FunctionalExchange 
                        connect source ::> 'Scan'.'FOP 2'
                        to target ::> 'Gather 35'.'FIP 1' { 
                        @CapellaID { eid = "93290df8-fed9-49d1-beed-b9aaf7a44f24"; sid = "93290df8-fed9-49d1-beed-b9aaf7a44f24"; } 
                        attribute :>> isMulticast = false; 
                        attribute :>> isMultireceive = false; 
                        attribute :>> kindOfRate = RateKind::Unspecified; 
                        attribute :>> interfaceName = "FunctionalExchange 21"; 
                         
                    }  
                    interface 'a9c8c5d1-a0aa-4fa8-9841-84cf667fb6e7' : FunctionalExchange 
                        connect source ::> 'Perform Overflight Recon Mission'.'Perform Scan'.'FOP 1'
                        to target ::> 'Activate Scan'.'FIP 2' { 
                        @CapellaID { eid = "a9c8c5d1-a0aa-4fa8-9841-84cf667fb6e7"; sid = "a9c8c5d1-a0aa-4fa8-9841-84cf667fb6e7"; } 
                        attribute :>> isMulticast = false; 
                        attribute :>> isMultireceive = false; 
                        attribute :>> kindOfRate = RateKind::Unspecified; 
                        attribute :>> interfaceName = "Scan"; 
                         
                    }  
                    interface 'efc215a0-6f00-45af-903a-ca7251958835' : FunctionalExchange 
                        connect source ::> 'Support Response'.'FOP 2'
                        to target ::> 'Provide Support'.'FIP 2' { 
                        @CapellaID { eid = "efc215a0-6f00-45af-903a-ca7251958835"; sid = "efc215a0-6f00-45af-903a-ca7251958835"; } 
                        attribute :>> isMulticast = false; 
                        attribute :>> isMultireceive = false; 
                        attribute :>> kindOfRate = RateKind::Unspecified; 
                        attribute :>> interfaceName = "FunctionalExchange 15"; 
                         
                    }  
                    interface 'e8af4590-715f-466e-ad38-6e47c27d2951' : FunctionalExchange 
                        connect source ::> 'Provide Support'.'FOP 1'
                        to target ::> 'Persons Supported'.'FIP 2' { 
                        @CapellaID { eid = "e8af4590-715f-466e-ad38-6e47c27d2951"; sid = "e8af4590-715f-466e-ad38-6e47c27d2951"; } 
                        attribute :>> isMulticast = false; 
                        attribute :>> isMultireceive = false; 
                        attribute :>> kindOfRate = RateKind::Unspecified; 
                        attribute :>> interfaceName = "FunctionalExchange 16"; 
                         
                    }  
                    interface 'f234bce6-52e7-49e9-bd9d-eeb5075a68b2' : FunctionalExchange 
                        connect source ::> 'Analysis'.'FOP 1'
                        to target ::> 'Perform Detect'.'FIP 4' { 
                        @CapellaID { eid = "f234bce6-52e7-49e9-bd9d-eeb5075a68b2"; } 
                        attribute :>> isMulticast = false; 
                        attribute :>> isMultireceive = false; 
                        attribute :>> kindOfRate = RateKind::Unspecified; 
                        attribute :>> interfaceName = "FunctionalExchange 50"; 
                         
                    }  
                    interface '4e29bbc1-ea33-40a6-a5a2-61e1dbf63ae6' : FunctionalExchange 
                        connect source ::> 'Interpreted Analysis Response'.'FOP 1'
                        to target ::> 'Support Response'.'FIP 1' { 
                        @CapellaID { eid = "4e29bbc1-ea33-40a6-a5a2-61e1dbf63ae6"; sid = "4e29bbc1-ea33-40a6-a5a2-61e1dbf63ae6"; } 
                        attribute :>> isMulticast = false; 
                        attribute :>> isMultireceive = false; 
                        attribute :>> kindOfRate = RateKind::Unspecified; 
                        attribute :>> interfaceName = "FunctionalExchange 26"; 
                         
                    }  
                    interface '4dd97418-d007-46d9-8f7c-87f3502c3ec5' : FunctionalExchange 
                        connect source ::> 'Analysis'.'FOP 2'
                        to target ::> 'Perform Overflight Recon Mission'.'Perform Scan'.'FIP 2' { 
                        @CapellaID { eid = "4dd97418-d007-46d9-8f7c-87f3502c3ec5"; sid = "4dd97418-d007-46d9-8f7c-87f3502c3ec5"; } 
                        attribute :>> isMulticast = false; 
                        attribute :>> isMultireceive = false; 
                        attribute :>> kindOfRate = RateKind::Unspecified; 
                        attribute :>> interfaceName = "FunctionalExchange 51"; 
                         
                    }  
                    interface 'f072ef8d-3125-471c-829f-6f95ca80097e' : FunctionalExchange 
                        connect source ::> 'Site Support'.'outInteraction 14'
                        to target ::> 'Persons Supported'.'inInteraction 14' { 
                        @CapellaID { eid = "f072ef8d-3125-471c-829f-6f95ca80097e"; sid = "f072ef8d-3125-471c-829f-6f95ca80097e"; } 
                        attribute :>> isMulticast = false; 
                        attribute :>> isMultireceive = false; 
                        attribute :>> kindOfRate = RateKind::Unspecified; 
                        attribute :>> interfaceName = "Interaction 14"; 
                         
                    }  
                    interface 'ad3df3f1-f31f-4b45-9438-4f06a86e4152' : FunctionalExchange 
                        connect source ::> 'Site Support'.'outInteraction 20'
                        to target ::> 'Action Report'.'inInteraction 20' { 
                        @CapellaID { eid = "ad3df3f1-f31f-4b45-9438-4f06a86e4152"; sid = "ad3df3f1-f31f-4b45-9438-4f06a86e4152"; } 
                        attribute :>> isMulticast = false; 
                        attribute :>> isMultireceive = false; 
                        attribute :>> kindOfRate = RateKind::Unspecified; 
                        attribute :>> interfaceName = "Interaction 20"; 
                         
                    }  
                    interface '98a1d99f-7d1b-4bf7-8389-e9648c7ba5c0' : FunctionalExchange 
                        connect source ::> 'Analysis'.'FOP 3'
                        to target ::> 'Interpret Analysis'.'FIP 1' { 
                        @CapellaID { eid = "98a1d99f-7d1b-4bf7-8389-e9648c7ba5c0"; } 
                        attribute :>> isMulticast = false; 
                        attribute :>> isMultireceive = false; 
                        attribute :>> kindOfRate = RateKind::Unspecified; 
                        attribute :>> interfaceName = "FunctionalExchange 54"; 
                         
                    }  
                    interface '4eb9f09b-b4e7-49a1-a73a-3346c16bd1f9' : FunctionalExchange 
                        connect source ::> 'Interpret Analysis'.'FOP 1'
                        to target ::> 'Interpreted Analysis Response'.'FIP 1' { 
                        @CapellaID { eid = "4eb9f09b-b4e7-49a1-a73a-3346c16bd1f9"; } 
                        attribute :>> isMulticast = false; 
                        attribute :>> isMultireceive = false; 
                        attribute :>> kindOfRate = RateKind::Unspecified; 
                        attribute :>> interfaceName = "FunctionalExchange 55"; 
                         
                    }  
                    interface '8aa7cbd4-27d0-4264-8599-c0c6acae31de' : FunctionalExchange 
                        connect source ::> 'Interpret Analysis'.'FOP 2'
                        to target ::> 'Process Data'.'FIP 1' { 
                        @CapellaID { eid = "8aa7cbd4-27d0-4264-8599-c0c6acae31de"; } 
                        attribute :>> isMulticast = false; 
                        attribute :>> isMultireceive = false; 
                        attribute :>> kindOfRate = RateKind::Unspecified; 
                        attribute :>> interfaceName = "FunctionalExchange 10"; 
                         
                    }  
                    interface 'd1a97504-b78b-41b9-acd8-4a02fb1a33c0' : FunctionalExchange 
                        connect source ::> 'Process Data'.'FOP 1'
                        to target ::> 'Perform Overflight Recon Mission'.'Perform Scan'.'FIP 1' { 
                        @CapellaID { eid = "d1a97504-b78b-41b9-acd8-4a02fb1a33c0"; sid = "d1a97504-b78b-41b9-acd8-4a02fb1a33c0"; } 
                        attribute :>> isMulticast = false; 
                        attribute :>> isMultireceive = false; 
                        attribute :>> kindOfRate = RateKind::Unspecified; 
                        attribute :>> interfaceName = "FunctionalExchange 11"; 
                         
                    }  
                    interface '42a21bb7-1b94-4ba2-86ea-e141e9b4c939' : FunctionalExchange 
                        connect source ::> 'Process Data'.'FOP 2'
                        to target ::> 'Perform Detect'.'FIP 1' { 
                        @CapellaID { eid = "42a21bb7-1b94-4ba2-86ea-e141e9b4c939"; } 
                        attribute :>> isMulticast = false; 
                        attribute :>> isMultireceive = false; 
                        attribute :>> kindOfRate = RateKind::Unspecified; 
                        attribute :>> interfaceName = "FunctionalExchange 12"; 
                         
                    }  
                    interface 'eef67666-861e-4bce-8358-80dc9d14d21b' : FunctionalExchange 
                        connect source ::> 'Process Data'.'FOP 3'
                        to target ::> 'Provide Support'.'FIP 1' { 
                        @CapellaID { eid = "eef67666-861e-4bce-8358-80dc9d14d21b"; } 
                        attribute :>> isMulticast = false; 
                        attribute :>> isMultireceive = false; 
                        attribute :>> kindOfRate = RateKind::Unspecified; 
                        attribute :>> interfaceName = "FunctionalExchange 13"; 
                         
                    }  
                    interface '9b5b76ce-98bf-45e6-9cfd-385ca0ce3e9d' : FunctionalExchange 
                        connect source ::> 'Action Report'.'FOP 1'
                        to target ::> 'xmit / xceive'.'FIP 1' { 
                        @CapellaID { eid = "9b5b76ce-98bf-45e6-9cfd-385ca0ce3e9d"; } 
                        attribute :>> isMulticast = false; 
                        attribute :>> isMultireceive = false; 
                        attribute :>> kindOfRate = RateKind::Unspecified; 
                        attribute :>> interfaceName = "FunctionalExchange 14"; 
                         
                    }  
                    interface '85a221ae-9eef-48ae-b69b-7979faced74a' : FunctionalExchange 
                        connect source ::> 'xmit / xceive'.'FOP 1'
                        to target ::> 'Process Data'.'FIP 2' { 
                        @CapellaID { eid = "85a221ae-9eef-48ae-b69b-7979faced74a"; } 
                        attribute :>> isMulticast = false; 
                        attribute :>> isMultireceive = false; 
                        attribute :>> kindOfRate = RateKind::Unspecified; 
                        attribute :>> interfaceName = "FunctionalExchange 15"; 
                         
                    }  
                    interface '92c595ae-1023-4c82-8220-7f2b2eb1bdd0' : FunctionalExchange 
                        connect source ::> 'Monitor Execution'.'outInteraction 22'
                        to target ::> 'Ad Hoc Mission Update'.'inInteraction 22' { 
                        @CapellaID { eid = "92c595ae-1023-4c82-8220-7f2b2eb1bdd0"; sid = "92c595ae-1023-4c82-8220-7f2b2eb1bdd0"; } 
                        attribute :>> isMulticast = false; 
                        attribute :>> isMultireceive = false; 
                        attribute :>> kindOfRate = RateKind::Unspecified; 
                        attribute :>> interfaceName = "Interaction 22"; 
                         
                    }  
                    interface 'a16b1418-33f2-4af9-b77b-52af39f442f4' : FunctionalExchange 
                        connect source ::> 'Provide C&amp;C SITREP'.'FOP 1'
                        to target ::> 'Monitor Execution'.'FIP 2' { 
                        @CapellaID { eid = "a16b1418-33f2-4af9-b77b-52af39f442f4"; sid = "a16b1418-33f2-4af9-b77b-52af39f442f4"; } 
                        attribute :>> isMulticast = false; 
                        attribute :>> isMultireceive = false; 
                        attribute :>> kindOfRate = RateKind::Unspecified; 
                        attribute :>> interfaceName = "FunctionalExchange 56"; 
                         
                    }  
                    interface '84a01918-f6c0-4f3b-9697-4a42fd16534e' : FunctionalExchange 
                        connect source ::> 'Update SITREP'.'FOP 1'
                        to target ::> 'Interpret SITREP'.'FIP 4' { 
                        @CapellaID { eid = "84a01918-f6c0-4f3b-9697-4a42fd16534e"; sid = "84a01918-f6c0-4f3b-9697-4a42fd16534e"; } 
                        attribute :>> isMulticast = false; 
                        attribute :>> isMultireceive = false; 
                        attribute :>> kindOfRate = RateKind::Unspecified; 
                        attribute :>> interfaceName = "FunctionalExchange 43"; 
                         
                    }  
                    interface '795262b4-e5cc-4f7e-b06e-7108bfe01fd4' : FunctionalExchange 
                        connect source ::> 'Interpret SITREP'.'FOP 1'
                        to target ::> 'Ad Hoc Mission Execution Update'.'FIP 1' { 
                        @CapellaID { eid = "795262b4-e5cc-4f7e-b06e-7108bfe01fd4"; sid = "795262b4-e5cc-4f7e-b06e-7108bfe01fd4"; } 
                        attribute :>> isMulticast = false; 
                        attribute :>> isMultireceive = false; 
                        attribute :>> kindOfRate = RateKind::Unspecified; 
                        attribute :>> interfaceName = "FunctionalExchange 44"; 
                         
                    }  
                    interface 'ab243386-52d7-459d-9707-6a18abbb9b83' : FunctionalExchange 
                        connect source ::> 'Ad Hoc Mission Update'.'FOP 1'
                        to target ::> 'Interpret SITREP'.'FIP 2' { 
                        @CapellaID { eid = "ab243386-52d7-459d-9707-6a18abbb9b83"; sid = "ab243386-52d7-459d-9707-6a18abbb9b83"; } 
                        attribute :>> isMulticast = false; 
                        attribute :>> isMultireceive = false; 
                        attribute :>> kindOfRate = RateKind::Unspecified; 
                        attribute :>> interfaceName = "FunctionalExchange 57"; 
                         
                    }  
                    interface '141959c3-cb9c-4778-88fa-dcf48fc230b3' : FunctionalExchange 
                        connect source ::> 'Ad Hoc Mission Execution Update'.'FOP 1'
                        to target ::> 'Ad Hoc Mission Update Response'.'FIP 1' { 
                        @CapellaID { eid = "141959c3-cb9c-4778-88fa-dcf48fc230b3"; sid = "141959c3-cb9c-4778-88fa-dcf48fc230b3"; } 
                        attribute :>> isMulticast = false; 
                        attribute :>> isMultireceive = false; 
                        attribute :>> kindOfRate = RateKind::Unspecified; 
                        attribute :>> interfaceName = "FunctionalExchange 48"; 
                         
                    }  
                    interface 'ff75426f-12a6-4208-8130-70b4c5c0c3f6' : FunctionalExchange 
                        connect source ::> 'Ad Hoc Mission Update Response'.'FOP 1'
                        to target ::> 'Update SITREP'.'FIP 4' { 
                        @CapellaID { eid = "ff75426f-12a6-4208-8130-70b4c5c0c3f6"; sid = "ff75426f-12a6-4208-8130-70b4c5c0c3f6"; } 
                        attribute :>> isMulticast = false; 
                        attribute :>> isMultireceive = false; 
                        attribute :>> kindOfRate = RateKind::Unspecified; 
                        attribute :>> interfaceName = "FunctionalExchange 58"; 
                         
                    }  
                    interface '1dc07bf7-2f2a-408a-b55d-537a90f10368' : FunctionalExchange 
                        connect source ::> 'Update SITREP'.'FOP 2'
                        to target ::> 'Provide C&amp;C SITREP'.'FIP 1' { 
                        @CapellaID { eid = "1dc07bf7-2f2a-408a-b55d-537a90f10368"; sid = "1dc07bf7-2f2a-408a-b55d-537a90f10368"; } 
                        attribute :>> isMulticast = false; 
                        attribute :>> isMultireceive = false; 
                        attribute :>> kindOfRate = RateKind::Unspecified; 
                        attribute :>> interfaceName = "FunctionalExchange 59"; 
                         
                    }  
                    interface '3f900ac2-d70a-4712-b1f3-2579db25b4e8' : FunctionalExchange 
                        connect source ::> 'Action Report'.'FOP 2'
                        to target ::> 'Update SITREP'.'FIP 2' { 
                        @CapellaID { eid = "3f900ac2-d70a-4712-b1f3-2579db25b4e8"; sid = "3f900ac2-d70a-4712-b1f3-2579db25b4e8"; } 
                        attribute :>> isMulticast = false; 
                        attribute :>> isMultireceive = false; 
                        attribute :>> kindOfRate = RateKind::Unspecified; 
                        attribute :>> interfaceName = "FunctionalExchange 60"; 
                         
                    }  
                    interface 'a60fd365-b419-40ea-b7ba-12a94748c12e' : FunctionalExchange 
                        connect source ::> 'Image Storage'.'outImages of trapped People'
                        to target ::> 'Locate Trapped People'.'inImages of trapped People' { 
                        @CapellaID { eid = "a60fd365-b419-40ea-b7ba-12a94748c12e"; sid = "a60fd365-b419-40ea-b7ba-12a94748c12e"; } 
                        attribute :>> isMulticast = false; 
                        attribute :>> isMultireceive = false; 
                        attribute :>> kindOfRate = RateKind::Unspecified; 
                        attribute :>> interfaceName = "Images of trapped People"; 
                         
                    }  
                    interface '844fdd8e-cc79-44c9-abe8-9d977e6bf76d' : FunctionalExchange 
                        connect source ::> 'Capture Photos'.'outPhotos'
                        to target ::> 'Image Storage'.'inPhotos' { 
                        @CapellaID { eid = "844fdd8e-cc79-44c9-abe8-9d977e6bf76d"; sid = "844fdd8e-cc79-44c9-abe8-9d977e6bf76d"; } 
                        attribute :>> isMulticast = false; 
                        attribute :>> isMultireceive = false; 
                        attribute :>> kindOfRate = RateKind::Unspecified; 
                        attribute :>> interfaceName = "Photos"; 
                         
                    }  
                    interface '12340e91-350b-40c8-8074-7d3584ea3bea' : FunctionalExchange 
                        connect source ::> 'Locate Trapped People'.'FOP 2'
                        to target ::> 'Relay to Operator'.'FIP 2' { 
                        @CapellaID { eid = "12340e91-350b-40c8-8074-7d3584ea3bea"; sid = "12340e91-350b-40c8-8074-7d3584ea3bea"; } 
                        attribute :>> isMulticast = false; 
                        attribute :>> isMultireceive = false; 
                        attribute :>> kindOfRate = RateKind::Unspecified; 
                        attribute :>> interfaceName = "Trapped People"; 
                         
                    }  
                    interface 'dab62d0a-f03a-4dc7-b11d-189881291644' : FunctionalExchange 
                        connect source ::> 'Natural Disaster '.'outImage'
                        to target ::> 'Capture Photos'.'inImage' { 
                        @CapellaID { eid = "dab62d0a-f03a-4dc7-b11d-189881291644"; sid = "dab62d0a-f03a-4dc7-b11d-189881291644"; } 
                        attribute :>> isMulticast = false; 
                        attribute :>> isMultireceive = false; 
                        attribute :>> kindOfRate = RateKind::Unspecified; 
                        attribute :>> interfaceName = "Image"; 
                         
                    }  
                    interface '1e89b679-4ee5-4fd3-8e47-a955e14e88a1' : FunctionalExchange 
                        connect source ::> 'Natural Disaster '.'outAudio Visual'
                        to target ::> 'Capture Video'.'inAudio Visual' { 
                        @CapellaID { eid = "1e89b679-4ee5-4fd3-8e47-a955e14e88a1"; sid = "1e89b679-4ee5-4fd3-8e47-a955e14e88a1"; } 
                        attribute :>> isMulticast = false; 
                        attribute :>> isMultireceive = false; 
                        attribute :>> kindOfRate = RateKind::Unspecified; 
                        attribute :>> interfaceName = "Audio Visual"; 
                         
                    }  
                    interface '71ada17d-39af-44a8-ab4d-4a1e92c6231e' : FunctionalExchange 
                        connect source ::> 'Relay Overflight Data from Drone Mission'.'outRecon Overflight Data'
                        to target ::> 'Collect Information  Distressed Location '.'inRecon Overflight Data' { 
                        @CapellaID { eid = "71ada17d-39af-44a8-ab4d-4a1e92c6231e"; sid = "71ada17d-39af-44a8-ab4d-4a1e92c6231e"; } 
                        attribute :>> isMulticast = false; 
                        attribute :>> isMultireceive = false; 
                        attribute :>> kindOfRate = RateKind::Unspecified; 
                        attribute :>> interfaceName = "Recon Overflight Data"; 
                         
                    }  
                    interface 'b141216c-80c6-4f2e-b648-67772db4f2b3' : FunctionalExchange 
                        connect source ::> 'Capture Video'.'outVideo'
                        to target ::> 'Image Storage'.'inVideo' { 
                        @CapellaID { eid = "b141216c-80c6-4f2e-b648-67772db4f2b3"; sid = "b141216c-80c6-4f2e-b648-67772db4f2b3"; } 
                        attribute :>> isMulticast = false; 
                        attribute :>> isMultireceive = false; 
                        attribute :>> kindOfRate = RateKind::Unspecified; 
                        attribute :>> interfaceName = "Video"; 
                         
                    }  
                    interface '85621e3d-1a84-45af-9235-c37b1a7aa9bd' : FunctionalExchange 
                        connect source ::> 'Locate Trapped People'.'outLocation'
                        to target ::> 'Relay Overflight Data from Drone Mission'.'inLocation' { 
                        @CapellaID { eid = "85621e3d-1a84-45af-9235-c37b1a7aa9bd"; sid = "85621e3d-1a84-45af-9235-c37b1a7aa9bd"; } 
                        attribute :>> isMulticast = false; 
                        attribute :>> isMultireceive = false; 
                        attribute :>> kindOfRate = RateKind::Unspecified; 
                        attribute :>> interfaceName = "Location"; 
                         
                    }  
                    interface '619f3dfd-edc3-4a6a-95f2-27ff70ec6afe' : FunctionalExchange 
                        connect source ::> 'Receive Mission Order'.'FOP 1'
                        to target ::> 'Operator Mission Planning'.'FIP 1' { 
                        @CapellaID { eid = "619f3dfd-edc3-4a6a-95f2-27ff70ec6afe"; sid = "619f3dfd-edc3-4a6a-95f2-27ff70ec6afe"; } 
                        attribute :>> isMulticast = false; 
                        attribute :>> isMultireceive = false; 
                        attribute :>> kindOfRate = RateKind::Unspecified; 
                        attribute :>> interfaceName = "FunctionalExchange 42"; 
                         
                    }  
                    interface '7de4d9d6-677f-49c9-8f58-fff49f71b043' : FunctionalExchange 
                        connect source ::> 'Define Overflight Recon Mission'.'outMIssion'
                        to target ::> 'Perform Overflight Recon Mission'.'inMIssion' { 
                        @CapellaID { eid = "7de4d9d6-677f-49c9-8f58-fff49f71b043"; sid = "7de4d9d6-677f-49c9-8f58-fff49f71b043"; } 
                        attribute :>> isMulticast = false; 
                        attribute :>> isMultireceive = false; 
                        attribute :>> kindOfRate = RateKind::Unspecified; 
                        attribute :>> interfaceName = "MIssion"; 
                         
                    }  
                    interface 'ff1adf05-fc1b-49b2-b2c8-df6a14d56eaf' : FunctionalExchange 
                        connect source ::> 'Relay to Operator'.'FOP 1'
                        to target ::> 'Support Response'.'FIP 2' { 
                        @CapellaID { eid = "ff1adf05-fc1b-49b2-b2c8-df6a14d56eaf"; sid = "ff1adf05-fc1b-49b2-b2c8-df6a14d56eaf"; } 
                        attribute :>> isMulticast = false; 
                        attribute :>> isMultireceive = false; 
                        attribute :>> kindOfRate = RateKind::Unspecified; 
                        attribute :>> interfaceName = "Trapped People"; 
                         
                    }  
                    interface 'bddbcd0d-3df2-4bff-95b1-9b19a6cdb267' : FunctionalExchange 
                        connect source ::> 'Persons Scanned'.'FOP 1'
                        to target ::> 'Capture Video'.'FIP 2' { 
                        @CapellaID { eid = "bddbcd0d-3df2-4bff-95b1-9b19a6cdb267"; sid = "bddbcd0d-3df2-4bff-95b1-9b19a6cdb267"; } 
                        attribute :>> isMulticast = false; 
                        attribute :>> isMultireceive = false; 
                        attribute :>> kindOfRate = RateKind::Unspecified; 
                        attribute :>> interfaceName = "Video"; 
                         
                    }  
                    interface '15984110-47d2-40e5-adc6-049128b8eb66' : FunctionalExchange 
                        connect source ::> 'Gather 35'.'FOP 1'
                        to target ::> 'Perform Overflight Recon Mission'.'Perform Scan'.'FIP 3' { 
                        @CapellaID { eid = "15984110-47d2-40e5-adc6-049128b8eb66"; sid = "15984110-47d2-40e5-adc6-049128b8eb66"; } 
                        attribute :>> isMulticast = false; 
                        attribute :>> isMultireceive = false; 
                        attribute :>> kindOfRate = RateKind::Unspecified; 
                        attribute :>> interfaceName = "Operator Commands"; 
                         
                    }  
                    interface '30c4fd48-fd98-416e-9086-feb98586279d' : FunctionalExchange 
                        connect source ::> 'Define Overflight Recon Mission'.'outMIssion'
                        to target ::> 'Operator Mission Planning'.'FIP 1' { 
                        @CapellaID { eid = "30c4fd48-fd98-416e-9086-feb98586279d"; sid = "30c4fd48-fd98-416e-9086-feb98586279d"; } 
                        attribute :>> isMulticast = false; 
                        attribute :>> isMultireceive = false; 
                        attribute :>> kindOfRate = RateKind::Unspecified; 
                        attribute :>> interfaceName = "No Name"; 
                         
                    }  
                    interface '4d82d33b-ac98-4319-bf5e-f8e2cab8e33d' : FunctionalExchange 
                        connect source ::> 'Support Response'.'FOP 2'
                        to target ::> 'Site Support'.'FIP 1' { 
                        @CapellaID { eid = "4d82d33b-ac98-4319-bf5e-f8e2cab8e33d"; sid = "4d82d33b-ac98-4319-bf5e-f8e2cab8e33d"; } 
                        attribute :>> isMulticast = false; 
                        attribute :>> isMultireceive = false; 
                        attribute :>> kindOfRate = RateKind::Unspecified; 
                        attribute :>> interfaceName = "Site Support"; 
                         
                    }  
                    interface '24a38b00-19b1-48de-850e-4f435028df88' : FunctionalExchange 
                        connect source ::> 'Activate Scan'.'FOP 1'
                        to target ::> 'Capture Video'.'FIP 3' { 
                        @CapellaID { eid = "24a38b00-19b1-48de-850e-4f435028df88"; sid = "24a38b00-19b1-48de-850e-4f435028df88"; } 
                        attribute :>> isMulticast = false; 
                        attribute :>> isMultireceive = false; 
                        attribute :>> kindOfRate = RateKind::Unspecified; 
                        attribute :>> interfaceName = "Capture Video"; 
                         
                    }  
                    interface '3636a890-f283-4557-8fbf-87c7fbd83013' : FunctionalExchange 
                        connect source ::> 'Activate Scan'.'FOP 2'
                        to target ::> 'Capture Photos'.'FIP 2' { 
                        @CapellaID { eid = "3636a890-f283-4557-8fbf-87c7fbd83013"; sid = "3636a890-f283-4557-8fbf-87c7fbd83013"; } 
                        attribute :>> isMulticast = false; 
                        attribute :>> isMultireceive = false; 
                        attribute :>> kindOfRate = RateKind::Unspecified; 
                        attribute :>> interfaceName = "Capture Photos"; 
                         
                    }  
                    interface '9a7c1e82-e3d2-4539-a01b-7569bbb0939f' : FunctionalExchange 
                        connect source ::> 'Image Storage'.'FOP 2'
                        to target ::> 'Relay Overflight Data from Drone Mission'.'FIP 2' { 
                        @CapellaID { eid = "9a7c1e82-e3d2-4539-a01b-7569bbb0939f"; sid = "9a7c1e82-e3d2-4539-a01b-7569bbb0939f"; } 
                        attribute :>> isMulticast = false; 
                        attribute :>> isMultireceive = false; 
                        attribute :>> kindOfRate = RateKind::Unspecified; 
                        attribute :>> interfaceName = "Image Data"; 
                         
                    }  
                    interface '96917dd7-0d19-4829-8049-ed4bfa50c570' : FunctionalExchange 
                        connect source ::> 'PhysicalFunction 40'.'FOP 1'
                        to target ::> 'PhysicalFunction 39'.'FIP 1' { 
                        @CapellaID { eid = "96917dd7-0d19-4829-8049-ed4bfa50c570"; } 
                        attribute :>> isMulticast = false; 
                        attribute :>> isMultireceive = false; 
                        attribute :>> kindOfRate = RateKind::Unspecified; 
                        attribute :>> interfaceName = "FunctionalExchange 46"; 
                         
                    }  
                    interface 'c9066143-21d9-48af-b056-4d1608b81bed' : FunctionalExchange 
                        connect source ::> 'PhysicalFunction 41'.'FOP 1'
                        to target ::> 'PhysicalFunction 40'.'FIP 1' { 
                        @CapellaID { eid = "c9066143-21d9-48af-b056-4d1608b81bed"; } 
                        attribute :>> isMulticast = false; 
                        attribute :>> isMultireceive = false; 
                        attribute :>> kindOfRate = RateKind::Unspecified; 
                        attribute :>> interfaceName = "FunctionalExchange 47"; 
                         
                    }  
                    interface '6224d738-93ed-415c-967f-5e125cf75016' : FunctionalExchange 
                        connect source ::> 'Supply H3 Pressure'.'FOP 1'
                        to target ::> 'Supply Pressure'.'FIP 1' { 
                        @CapellaID { eid = "6224d738-93ed-415c-967f-5e125cf75016"; sid = "6224d738-93ed-415c-967f-5e125cf75016"; } 
                        attribute :>> isMulticast = false; 
                        attribute :>> isMultireceive = false; 
                        attribute :>> kindOfRate = RateKind::Unspecified; 
                        attribute :>> interfaceName = "No. 2 Hydraulic System"; 
                         
                    }  
                    interface '41b60723-f7c9-414c-9e34-2b50804b839b' : FunctionalExchange 
                        connect source ::> 'Supply H3 Pressure'.'FOP 2'
                        to target ::> 'SupplyPressur'.'FIP 2' { 
                        @CapellaID { eid = "41b60723-f7c9-414c-9e34-2b50804b839b"; sid = "41b60723-f7c9-414c-9e34-2b50804b839b"; } 
                        attribute :>> isMulticast = false; 
                        attribute :>> isMultireceive = false; 
                        attribute :>> kindOfRate = RateKind::Unspecified; 
                        attribute :>> interfaceName = "No. 3 Hydraulic System"; 
                         
                    }  
                    interface 'af1f32da-c8de-4166-8d67-a8a392ae3cca' : FunctionalExchange 
                        connect source ::> 'Sense Pressure'.'FOP 1'
                        to target ::> 'Supply H3 Pressure'.'FIP 1' { 
                        @CapellaID { eid = "af1f32da-c8de-4166-8d67-a8a392ae3cca"; } 
                        attribute :>> isMulticast = false; 
                        attribute :>> isMultireceive = false; 
                        attribute :>> kindOfRate = RateKind::Unspecified; 
                        attribute :>> interfaceName = "Commands"; 
                         
                    }  
                    interface '7face944-9535-447d-a41b-045e590a65dd' : FunctionalExchange 
                        connect source ::> 'Sense Pressure'.'FOP 1'
                        to target ::> 'Provide Landing Gear Control'.'Provide'.'FIP 1' { 
                        @CapellaID { eid = "7face944-9535-447d-a41b-045e590a65dd"; } 
                        attribute :>> isMulticast = false; 
                        attribute :>> isMultireceive = false; 
                        attribute :>> kindOfRate = RateKind::Unspecified; 
                        attribute :>> interfaceName = "Commands"; 
                         
                    }  
                    interface '476a9f9a-b908-470d-8d8b-0b443489cb84' : FunctionalExchange 
                        connect source ::> 'Provide'.'FOP 1'
                        to target ::> 'Provide Landing Gear Control'.'Provide'.'FIP 2' { 
                        @CapellaID { eid = "476a9f9a-b908-470d-8d8b-0b443489cb84"; } 
                        attribute :>> isMulticast = false; 
                        attribute :>> isMultireceive = false; 
                        attribute :>> kindOfRate = RateKind::Unspecified; 
                        attribute :>> interfaceName = "Aircraft Generator Power"; 
                         
                    }  
                    interface '5620edc6-3057-4812-906f-d26b02ad52dd' : FunctionalExchange 
                        connect source ::> 'Support '.'FOP 1'
                        to target ::> 'Duplicate 67'.'FIP 1' { 
                        @CapellaID { eid = "5620edc6-3057-4812-906f-d26b02ad52dd"; sid = "5620edc6-3057-4812-906f-d26b02ad52dd"; } 
                        attribute :>> isMulticast = false; 
                        attribute :>> isMultireceive = false; 
                        attribute :>> kindOfRate = RateKind::Unspecified; 
                        attribute :>> interfaceName = "Structural"; 
                         
                    }  
                    interface '6f08837b-eae6-40ce-b08c-aca538a78912' : FunctionalExchange 
                        connect source ::> 'Provide Landing Gear Indication'.'Provide'.'FOP 1'
                        to target ::> 'Provide Status'.'FIP 1' { 
                        @CapellaID { eid = "6f08837b-eae6-40ce-b08c-aca538a78912"; sid = "6f08837b-eae6-40ce-b08c-aca538a78912"; } 
                        attribute :>> isMulticast = false; 
                        attribute :>> isMultireceive = false; 
                        attribute :>> kindOfRate = RateKind::Unspecified; 
                        attribute :>> interfaceName = "LG Status"; 
                         
                    }  
                    interface 'adb0d0e1-fdb9-48dd-9e01-1c9444a10c8e' : FunctionalExchange 
                        connect source ::> 'Support LG'.'Gather 6'.'FOP 1'
                        to target ::> 'Provide Ground  Force'.'FIP 1' { 
                        @CapellaID { eid = "adb0d0e1-fdb9-48dd-9e01-1c9444a10c8e"; } 
                        attribute :>> isMulticast = false; 
                        attribute :>> isMultireceive = false; 
                        attribute :>> kindOfRate = RateKind::Unspecified; 
                        attribute :>> interfaceName = "Airplane weight on NLG"; 
                         
                    }  
                    interface '7fbdfbe1-b89b-4fbb-88f9-bc65dfbc1379' : FunctionalExchange 
                        connect source ::> 'Support LG'.'Gather 5'.'FOP 4'
                        to target ::> 'Provide Friction'.'FIP 1' { 
                        @CapellaID { eid = "7fbdfbe1-b89b-4fbb-88f9-bc65dfbc1379"; } 
                        attribute :>> isMulticast = false; 
                        attribute :>> isMultireceive = false; 
                        attribute :>> kindOfRate = RateKind::Unspecified; 
                        attribute :>> interfaceName = "NLG Heat Dissipation"; 
                         
                    }  
                    interface 'f387bf1c-81b3-444b-903f-9b1aa25c00f1' : FunctionalExchange 
                        connect source ::> 'Transmit NLG Forces'.'Transmit NLG Structural Post'.'FOP 6'
                        to target ::> 'Provide Friction'.'FIP 3' { 
                        @CapellaID { eid = "f387bf1c-81b3-444b-903f-9b1aa25c00f1"; } 
                        attribute :>> isMulticast = false; 
                        attribute :>> isMultireceive = false; 
                        attribute :>> kindOfRate = RateKind::Unspecified; 
                        attribute :>> interfaceName = "MLG Right Heat Dicispation"; 
                         
                    }  
                    interface '5441eb90-cfa9-4f55-96de-54e7625462c1' : FunctionalExchange 
                        connect source ::> 'Transmit Ground Force'.'FOP 1'
                        to target ::> 'Transmit LG Force'.'FIP 1' { 
                        @CapellaID { eid = "5441eb90-cfa9-4f55-96de-54e7625462c1"; sid = "5441eb90-cfa9-4f55-96de-54e7625462c1"; } 
                        attribute :>> isMulticast = false; 
                        attribute :>> isMultireceive = false; 
                        attribute :>> kindOfRate = RateKind::Unspecified; 
                        attribute :>> interfaceName = " RMLG Structural Post Landing and Taxi Loads"; 
                         
                    }  
                    interface '73b4b16a-bf09-4603-81c1-9748d4dae983' : FunctionalExchange 
                        connect source ::> 'Tranmit'.'FOP 2'
                        to target ::> 'Transmit LG Force'.'FIP 2' { 
                        @CapellaID { eid = "73b4b16a-bf09-4603-81c1-9748d4dae983"; sid = "73b4b16a-bf09-4603-81c1-9748d4dae983"; } 
                        attribute :>> isMulticast = false; 
                        attribute :>> isMultireceive = false; 
                        attribute :>> kindOfRate = RateKind::Unspecified; 
                        attribute :>> interfaceName = " LMLG Structural Post Landing and Taxi Loads"; 
                         
                    }  
                    interface '3dd2c494-03e4-4511-8229-90df30f2fb6a' : FunctionalExchange 
                        connect source ::> 'Transmit LG Force'.'FOP 1'
                        to target ::> 'Support '.'FIP 4' { 
                        @CapellaID { eid = "3dd2c494-03e4-4511-8229-90df30f2fb6a"; sid = "3dd2c494-03e4-4511-8229-90df30f2fb6a"; } 
                        attribute :>> isMulticast = false; 
                        attribute :>> isMultireceive = false; 
                        attribute :>> kindOfRate = RateKind::Unspecified; 
                        attribute :>> interfaceName = "Aircraft Structure"; 
                         
                    }  
                    interface 'e586d180-2195-4911-ae8a-04dcef046776' : FunctionalExchange 
                        connect source ::> 'Sense Hardware'.'Sense NLG Door Position'.'FOP 1'
                        to target ::> 'Sense NLG State'.'FIP 1' { 
                        @CapellaID { eid = "e586d180-2195-4911-ae8a-04dcef046776"; sid = "e586d180-2195-4911-ae8a-04dcef046776"; } 
                        attribute :>> isMulticast = false; 
                        attribute :>> isMultireceive = false; 
                        attribute :>> kindOfRate = RateKind::Unspecified; 
                        attribute :>> interfaceName = "NLG Door Position"; 
                         
                    }  
                    interface 'e464a43f-96dd-4638-84e3-50dcae0fc54c' : FunctionalExchange 
                        connect source ::> 'Sense Hardware'.'Sense DWNLock Position 1'.'FOP 2'
                        to target ::> 'Sense NLG State'.'FIP 2' { 
                        @CapellaID { eid = "e464a43f-96dd-4638-84e3-50dcae0fc54c"; sid = "e464a43f-96dd-4638-84e3-50dcae0fc54c"; } 
                        attribute :>> isMulticast = false; 
                        attribute :>> isMultireceive = false; 
                        attribute :>> kindOfRate = RateKind::Unspecified; 
                        attribute :>> interfaceName = "NLG DWNLock Position 1"; 
                         
                    }  
                    interface '2dc4a6c7-e5da-4c4b-b985-c50c84750e56' : FunctionalExchange 
                        connect source ::> 'Sense Hardware'.'Sense DWNLock Position 2'.'FOP 3'
                        to target ::> 'Sense NLG State'.'FIP 3' { 
                        @CapellaID { eid = "2dc4a6c7-e5da-4c4b-b985-c50c84750e56"; sid = "2dc4a6c7-e5da-4c4b-b985-c50c84750e56"; } 
                        attribute :>> isMulticast = false; 
                        attribute :>> isMultireceive = false; 
                        attribute :>> kindOfRate = RateKind::Unspecified; 
                        attribute :>> interfaceName = "NLG DWNLock Position 2"; 
                         
                    }  
                    interface '0fe580e4-7e35-48b1-898c-3d7c1f790ec8' : FunctionalExchange 
                        connect source ::> 'Sense Hardware'.'Sense NLG Uplock Position 1'.'FOP 4'
                        to target ::> 'Sense NLG State'.'FIP 4' { 
                        @CapellaID { eid = "0fe580e4-7e35-48b1-898c-3d7c1f790ec8"; sid = "0fe580e4-7e35-48b1-898c-3d7c1f790ec8"; } 
                        attribute :>> isMulticast = false; 
                        attribute :>> isMultireceive = false; 
                        attribute :>> kindOfRate = RateKind::Unspecified; 
                        attribute :>> interfaceName = "NLG UPLock Position Sensor1"; 
                         
                    }  
                    interface '800ff49e-cc73-4b71-9e22-27283841597f' : FunctionalExchange 
                        connect source ::> 'Sense Hardware'.'Sense UPLock Position 2'.'FOP 5'
                        to target ::> 'Sense NLG State'.'FIP 5' { 
                        @CapellaID { eid = "800ff49e-cc73-4b71-9e22-27283841597f"; sid = "800ff49e-cc73-4b71-9e22-27283841597f"; } 
                        attribute :>> isMulticast = false; 
                        attribute :>> isMultireceive = false; 
                        attribute :>> kindOfRate = RateKind::Unspecified; 
                        attribute :>> interfaceName = "NLG UPLock Position Sensor2"; 
                         
                    }  
                    interface '59428dfe-81b6-4d97-8654-c1d4bfb73819' : FunctionalExchange 
                        connect source ::> 'SupplyPressur'.'FOP 5'
                        to target ::> 'Measure'.'Actuate NLG'.'Control Pressure to Wheel'.'FIP 1' { 
                        @CapellaID { eid = "59428dfe-81b6-4d97-8654-c1d4bfb73819"; sid = "59428dfe-81b6-4d97-8654-c1d4bfb73819"; } 
                        attribute :>> isMulticast = false; 
                        attribute :>> isMultireceive = false; 
                        attribute :>> kindOfRate = RateKind::Unspecified; 
                        attribute :>> interfaceName = "No. 3 Hydraulic System"; 
                         
                    }  
                    interface '16a8d621-e576-4365-bbb3-e65bea6bff08' : FunctionalExchange 
                        connect source ::> 'Measure'.'Actuate NLG'.'Apply Force Runway'.'FOP 3'
                        to target ::> 'Transmit NLG Forces'.'Dampen Spring'.'FIP 1' { 
                        @CapellaID { eid = "16a8d621-e576-4365-bbb3-e65bea6bff08"; sid = "16a8d621-e576-4365-bbb3-e65bea6bff08"; } 
                        attribute :>> isMulticast = false; 
                        attribute :>> isMultireceive = false; 
                        attribute :>> kindOfRate = RateKind::Unspecified; 
                        attribute :>> interfaceName = "Landing and Taxi Loads"; 
                         
                    }  
                    interface '2ac5535d-5a1f-448f-9a24-cdb778d6e8db' : FunctionalExchange 
                        connect source ::> 'Supply Pressure'.'FOP 1'
                        to target ::> 'SupplyPressur'.'FIP 1' { 
                        @CapellaID { eid = "2ac5535d-5a1f-448f-9a24-cdb778d6e8db"; sid = "2ac5535d-5a1f-448f-9a24-cdb778d6e8db"; } 
                        attribute :>> isMulticast = false; 
                        attribute :>> isMultireceive = false; 
                        attribute :>> kindOfRate = RateKind::Unspecified; 
                        attribute :>> interfaceName = "No. 2 Hydraulic System"; 
                         
                    }  
                    interface '51e005b5-44cd-4c32-a336-21bb4f8f1408' : FunctionalExchange 
                        connect source ::> 'Supply Pressure'.'FOP 2'
                        to target ::> 'Measure'.'FIP 2' { 
                        @CapellaID { eid = "51e005b5-44cd-4c32-a336-21bb4f8f1408"; } 
                        attribute :>> isMulticast = false; 
                        attribute :>> isMultireceive = false; 
                        attribute :>> kindOfRate = RateKind::Unspecified; 
                        attribute :>> interfaceName = "No. 2 Hydraulic System"; 
                         
                    }  
                    interface 'e8026413-6760-47f1-bdb5-eff8b873c988' : FunctionalExchange 
                        connect source ::> 'Duplicate 67'.'FOP 2'
                        to target ::> 'Transmit NLG Forces'.'Transmit NLG Structural Post'.'FIP 3' { 
                        @CapellaID { eid = "e8026413-6760-47f1-bdb5-eff8b873c988"; sid = "e8026413-6760-47f1-bdb5-eff8b873c988"; } 
                        attribute :>> isMulticast = false; 
                        attribute :>> isMultireceive = false; 
                        attribute :>> kindOfRate = RateKind::Unspecified; 
                        attribute :>> interfaceName = "Structural"; 
                         
                    }  
                    interface '08a41a71-a931-4311-9987-7d9fe0971867' : FunctionalExchange 
                        connect source ::> 'Duplicate 67'.'FOP 3'
                        to target ::> 'Support LG'.'Duplicate 4'.'FIP 1' { 
                        @CapellaID { eid = "08a41a71-a931-4311-9987-7d9fe0971867"; sid = "08a41a71-a931-4311-9987-7d9fe0971867"; } 
                        attribute :>> isMulticast = false; 
                        attribute :>> isMultireceive = false; 
                        attribute :>> kindOfRate = RateKind::Unspecified; 
                        attribute :>> interfaceName = "Structural"; 
                         
                    }  
                    interface 'e51a349f-3ff9-42b6-901f-f07199aa65c3' : FunctionalExchange 
                        connect source ::> 'Sense Hardware'.'Sense Shock Position 2'.'FOP 6'
                        to target ::> 'Sense NLG State'.'FIP 17' { 
                        @CapellaID { eid = "e51a349f-3ff9-42b6-901f-f07199aa65c3"; sid = "e51a349f-3ff9-42b6-901f-f07199aa65c3"; } 
                        attribute :>> isMulticast = false; 
                        attribute :>> isMultireceive = false; 
                        attribute :>> kindOfRate = RateKind::Unspecified; 
                        attribute :>> interfaceName = "NLG Shock Position 2"; 
                         
                    }  
                    interface 'a9bde180-4f8d-42a5-b923-4e4752822080' : FunctionalExchange 
                        connect source ::> 'Sense Hardware'.'Sense Shock Position 1'.'FOP 7'
                        to target ::> 'Sense NLG State'.'FIP 19' { 
                        @CapellaID { eid = "a9bde180-4f8d-42a5-b923-4e4752822080"; sid = "a9bde180-4f8d-42a5-b923-4e4752822080"; } 
                        attribute :>> isMulticast = false; 
                        attribute :>> isMultireceive = false; 
                        attribute :>> kindOfRate = RateKind::Unspecified; 
                        attribute :>> interfaceName = "NLG Shock Position 1 "; 
                         
                    }  
                    interface '4c3fd424-a65e-46d2-8687-718dfacf40e2' : FunctionalExchange 
                        connect source ::> 'Provide Landing Gear Control'.'Provide'.'FOP 1'
                        to target ::> 'Sense NLG State'.'FIP 20' { 
                        @CapellaID { eid = "4c3fd424-a65e-46d2-8687-718dfacf40e2"; sid = "4c3fd424-a65e-46d2-8687-718dfacf40e2"; } 
                        attribute :>> isMulticast = false; 
                        attribute :>> isMultireceive = false; 
                        attribute :>> kindOfRate = RateKind::Unspecified; 
                        attribute :>> interfaceName = "Extension Retraction Command"; 
                         
                    }  
                    interface '95abeb94-ee12-44d8-96f4-de9c3e32badf' : FunctionalExchange 
                        connect source ::> 'Manage NLG'.'FOP 1'
                        to target ::> 'Measure'.'Actuate NLG'.'Control Pressure to Wheel'.'FIP 3' { 
                        @CapellaID { eid = "95abeb94-ee12-44d8-96f4-de9c3e32badf"; sid = "95abeb94-ee12-44d8-96f4-de9c3e32badf"; } 
                        attribute :>> isMulticast = false; 
                        attribute :>> isMultireceive = false; 
                        attribute :>> kindOfRate = RateKind::Unspecified; 
                        attribute :>> interfaceName = "Retract"; 
                         
                    }  
                    interface '89842b61-fafa-4233-803f-5059b8ac41da' : FunctionalExchange 
                        connect source ::> 'Sense NLG State'.'FOP 5'
                        to target ::> 'Manage NLG'.'FIP 3' { 
                        @CapellaID { eid = "89842b61-fafa-4233-803f-5059b8ac41da"; sid = "89842b61-fafa-4233-803f-5059b8ac41da"; } 
                        attribute :>> isMulticast = false; 
                        attribute :>> isMultireceive = false; 
                        attribute :>> kindOfRate = RateKind::Unspecified; 
                        attribute :>> interfaceName = "Extend"; 
                         
                    }  
                    interface 'cc844e5e-66ad-40b1-b1de-388d7aaafd88' : FunctionalExchange 
                        connect source ::> 'SupplyPressur'.'FOP 1'
                        to target ::> 'ActuateLMLG'.'FIP 1' { 
                        @CapellaID { eid = "cc844e5e-66ad-40b1-b1de-388d7aaafd88"; sid = "cc844e5e-66ad-40b1-b1de-388d7aaafd88"; } 
                        attribute :>> isMulticast = false; 
                        attribute :>> isMultireceive = false; 
                        attribute :>> kindOfRate = RateKind::Unspecified; 
                        attribute :>> interfaceName = "No. 2 Hydraulic System"; 
                         
                    }  
                    interface 'dee65853-313f-4ca0-974d-7c0587c78f7d' : FunctionalExchange 
                        connect source ::> 'SupplyPressur'.'FOP 2'
                        to target ::> 'Actuate RMLG'.'FIP 1' { 
                        @CapellaID { eid = "dee65853-313f-4ca0-974d-7c0587c78f7d"; sid = "dee65853-313f-4ca0-974d-7c0587c78f7d"; } 
                        attribute :>> isMulticast = false; 
                        attribute :>> isMultireceive = false; 
                        attribute :>> kindOfRate = RateKind::Unspecified; 
                        attribute :>> interfaceName = "No. 3 Hydraulic System"; 
                         
                    }  
                    interface 'e1a8badb-13d4-4949-b989-39677c7349da' : FunctionalExchange 
                        connect source ::> 'SupplyPressur'.'FOP 3'
                        to target ::> 'Actuate RMLG'.'FIP 2' { 
                        @CapellaID { eid = "e1a8badb-13d4-4949-b989-39677c7349da"; sid = "e1a8badb-13d4-4949-b989-39677c7349da"; } 
                        attribute :>> isMulticast = false; 
                        attribute :>> isMultireceive = false; 
                        attribute :>> kindOfRate = RateKind::Unspecified; 
                        attribute :>> interfaceName = "No. 2 Hydraulic System"; 
                         
                    }  
                    interface 'b9cdc645-a99b-4cb1-a8c8-5111fdd8db62' : FunctionalExchange 
                        connect source ::> 'SupplyPressur'.'FOP 4'
                        to target ::> 'ActuateLMLG'.'FIP 2' { 
                        @CapellaID { eid = "b9cdc645-a99b-4cb1-a8c8-5111fdd8db62"; sid = "b9cdc645-a99b-4cb1-a8c8-5111fdd8db62"; } 
                        attribute :>> isMulticast = false; 
                        attribute :>> isMultireceive = false; 
                        attribute :>> kindOfRate = RateKind::Unspecified; 
                        attribute :>> interfaceName = "No. 3 Hydraulic System"; 
                         
                    }  
                    interface '374b5c8a-4916-4a0d-a034-b81b7ac79b2a' : FunctionalExchange 
                        connect source ::> 'Sense NLG State'.'FOP 6'
                        to target ::> 'Provide Landing Gear Indication'.'Provide'.'FIP 1' { 
                        @CapellaID { eid = "374b5c8a-4916-4a0d-a034-b81b7ac79b2a"; sid = "374b5c8a-4916-4a0d-a034-b81b7ac79b2a"; } 
                        attribute :>> isMulticast = false; 
                        attribute :>> isMultireceive = false; 
                        attribute :>> kindOfRate = RateKind::Unspecified; 
                        attribute :>> interfaceName = "LG Status"; 
                         
                    }  
                    interface 'ae78d464-1d1a-4c52-85da-8e596ee0dd6b' : FunctionalExchange 
                        connect source ::> 'Control'.'FOP 1'
                        to target ::> 'Channel'.'FIP 2' { 
                        @CapellaID { eid = "ae78d464-1d1a-4c52-85da-8e596ee0dd6b"; } 
                        attribute :>> isMulticast = false; 
                        attribute :>> isMultireceive = false; 
                        attribute :>> kindOfRate = RateKind::Unspecified; 
                        attribute :>> interfaceName = "FunctionalExchange 9"; 
                         
                    }  
                    interface '9fc76035-36cb-46e9-af40-9f319ce9dd9b' : FunctionalExchange 
                        connect source ::> 'Isolate '.'FOP 1'
                        to target ::> 'Control'.'FIP 1' { 
                        @CapellaID { eid = "9fc76035-36cb-46e9-af40-9f319ce9dd9b"; } 
                        attribute :>> isMulticast = false; 
                        attribute :>> isMultireceive = false; 
                        attribute :>> kindOfRate = RateKind::Unspecified; 
                        attribute :>> interfaceName = "Fluid"; 
                         
                    }  
                    interface '76d4943d-d74b-4546-84d1-4e6ac62e216e' : FunctionalExchange 
                        connect source ::> 'Pump Fliud'.'FOP 1'
                        to target ::> 'Regulate'.'FIP 1' { 
                        @CapellaID { eid = "76d4943d-d74b-4546-84d1-4e6ac62e216e"; } 
                        attribute :>> isMulticast = false; 
                        attribute :>> isMultireceive = false; 
                        attribute :>> kindOfRate = RateKind::Unspecified; 
                        attribute :>> interfaceName = "Fluid"; 
                         
                    }  
                    interface 'd3106823-a315-407a-9dbc-d9d2512ba147' : FunctionalExchange 
                        connect source ::> 'Store'.'FOP 1'
                        to target ::> 'Channel'.'FIP 1' { 
                        @CapellaID { eid = "d3106823-a315-407a-9dbc-d9d2512ba147"; } 
                        attribute :>> isMulticast = false; 
                        attribute :>> isMultireceive = false; 
                        attribute :>> kindOfRate = RateKind::Unspecified; 
                        attribute :>> interfaceName = "Fluid"; 
                         
                    }  
                    interface '77535c9e-26f9-48f9-a652-dccbb875f365' : FunctionalExchange 
                        connect source ::> 'Pump Fluid'.'FOP 1'
                        to target ::> 'Isolate '.'FIP 1' { 
                        @CapellaID { eid = "77535c9e-26f9-48f9-a652-dccbb875f365"; } 
                        attribute :>> isMulticast = false; 
                        attribute :>> isMultireceive = false; 
                        attribute :>> kindOfRate = RateKind::Unspecified; 
                        attribute :>> interfaceName = "Fluid"; 
                         
                    }  
                    interface '678f50d6-4c8e-4ae7-8486-c5cae7f377e4' : FunctionalExchange 
                        connect source ::> 'Store'.'FOP 2'
                        to target ::> 'Maintain Pressure'.'FIP 1' { 
                        @CapellaID { eid = "678f50d6-4c8e-4ae7-8486-c5cae7f377e4"; } 
                        attribute :>> isMulticast = false; 
                        attribute :>> isMultireceive = false; 
                        attribute :>> kindOfRate = RateKind::Unspecified; 
                        attribute :>> interfaceName = "Pressure"; 
                         
                    }  
                    interface '40cd96ef-accd-416b-8716-89d7c25477f3' : FunctionalExchange 
                        connect source ::> 'Regulate'.'FOP 1'
                        to target ::> 'Control'.'FIP 2' { 
                        @CapellaID { eid = "40cd96ef-accd-416b-8716-89d7c25477f3"; } 
                        attribute :>> isMulticast = false; 
                        attribute :>> isMultireceive = false; 
                        attribute :>> kindOfRate = RateKind::Unspecified; 
                        attribute :>> interfaceName = "Fluid"; 
                         
                    }  
                    interface 'c1721ee8-7264-4c86-887b-39c3bbad311c' : FunctionalExchange 
                        connect source ::> 'Maintain Pressure'.'FOP 1'
                        to target ::> 'Store'.'FIP 1' { 
                        @CapellaID { eid = "c1721ee8-7264-4c86-887b-39c3bbad311c"; } 
                        attribute :>> isMulticast = false; 
                        attribute :>> isMultireceive = false; 
                        attribute :>> kindOfRate = RateKind::Unspecified; 
                        attribute :>> interfaceName = "Pressure"; 
                         
                    }  
                    interface '7cee4409-2d70-49cf-9ffa-b6541a64d7e4' : FunctionalExchange 
                        connect source ::> 'Measure'.'Actuate NLG'.'Apply Force Runway'.'FOP 1'
                        to target ::> 'Provide Ground  Force'.'FIP 4' { 
                        @CapellaID { eid = "7cee4409-2d70-49cf-9ffa-b6541a64d7e4"; sid = "7cee4409-2d70-49cf-9ffa-b6541a64d7e4"; } 
                        attribute :>> isMulticast = false; 
                        attribute :>> isMultireceive = false; 
                        attribute :>> kindOfRate = RateKind::Unspecified; 
                        attribute :>> interfaceName = "Deliver Lateral Force"; 
                         
                    }  
                    interface 'cd3e88dc-1a45-4457-bb04-6d0229ca538f' : FunctionalExchange 
                        connect source ::> 'PhysicalFunction 39'.'FOP 1'
                        to target ::> 'Regulate'.'FIP 2' { 
                        @CapellaID { eid = "cd3e88dc-1a45-4457-bb04-6d0229ca538f"; } 
                        attribute :>> isMulticast = false; 
                        attribute :>> isMultireceive = false; 
                        attribute :>> kindOfRate = RateKind::Unspecified; 
                        attribute :>> interfaceName = "Brake Control"; 
                         
                    }  
                    interface '14d27697-47bf-4616-9758-b1dd5dcf8edf' : FunctionalExchange 
                        connect source ::> 'Slow Rotation'.'FOP 1'
                        to target ::> 'Provide Friction'.'FIP 5' { 
                        @CapellaID { eid = "14d27697-47bf-4616-9758-b1dd5dcf8edf"; sid = "14d27697-47bf-4616-9758-b1dd5dcf8edf"; } 
                        attribute :>> isMulticast = false; 
                        attribute :>> isMultireceive = false; 
                        attribute :>> kindOfRate = RateKind::Unspecified; 
                        attribute :>> interfaceName = "Deliver Rolling Force"; 
                         
                    }  
                    interface '34a60779-44ba-4915-af24-5fd1877d6cad' : FunctionalExchange 
                        connect source ::> 'Channel'.'FOP 1'
                        to target ::> 'Slow Rotation'.'FIP 1' { 
                        @CapellaID { eid = "34a60779-44ba-4915-af24-5fd1877d6cad"; sid = "34a60779-44ba-4915-af24-5fd1877d6cad"; } 
                        attribute :>> isMulticast = false; 
                        attribute :>> isMultireceive = false; 
                        attribute :>> kindOfRate = RateKind::Unspecified; 
                        attribute :>> interfaceName = "Brake Line Fluid Pressure"; 
                         
                    }  
                    interface '1d0ef78d-bb0c-4929-ace7-8d0818fef271' : FunctionalExchange 
                        connect source ::> 'Sense Weight on Wheels'.'FOP 1'
                        to target ::> 'Sense NLG State'.'FIP 21' { 
                        @CapellaID { eid = "1d0ef78d-bb0c-4929-ace7-8d0818fef271"; } 
                        attribute :>> isMulticast = false; 
                        attribute :>> isMultireceive = false; 
                        attribute :>> kindOfRate = RateKind::Unspecified; 
                        attribute :>> interfaceName = "Weight on Wheels 1"; 
                         
                    }  
                    interface '004b4ee4-f50b-47d8-8ab8-684a3165d440' : FunctionalExchange 
                        connect source ::> 'Sense Weight on Wheels 2'.'FOP 1'
                        to target ::> 'Sense NLG State'.'FIP 22' { 
                        @CapellaID { eid = "004b4ee4-f50b-47d8-8ab8-684a3165d440"; } 
                        attribute :>> isMulticast = false; 
                        attribute :>> isMultireceive = false; 
                        attribute :>> kindOfRate = RateKind::Unspecified; 
                        attribute :>> interfaceName = "Weight on Wheels 2"; 
                         
                    }  
                    interface '832de532-5107-4edb-a0e5-b610d918034f' : FunctionalExchange 
                        connect source ::> 'Transmit NLG Forces'.'Transmit NLG Structural Post'.'FOP 3'
                        to target ::> 'Provide Spring Support'.'FIP 1' { 
                        @CapellaID { eid = "832de532-5107-4edb-a0e5-b610d918034f"; } 
                        attribute :>> isMulticast = false; 
                        attribute :>> isMultireceive = false; 
                        attribute :>> kindOfRate = RateKind::Unspecified; 
                        attribute :>> interfaceName = "Structural Load"; 
                         
                    }  
                    interface 'e3479523-c52a-4d52-a6fd-5c74b60d7431' : FunctionalExchange 
                        connect source ::> 'Transmit NLG Forces'.'Transmit NLG Structural Post'.'FOP 1'
                        to target ::> 'Support LG'.'Gather 5'.'FIP 1' { 
                        @CapellaID { eid = "e3479523-c52a-4d52-a6fd-5c74b60d7431"; sid = "e3479523-c52a-4d52-a6fd-5c74b60d7431"; } 
                        attribute :>> isMulticast = false; 
                        attribute :>> isMultireceive = false; 
                        attribute :>> kindOfRate = RateKind::Unspecified; 
                        attribute :>> interfaceName = "Structural"; 
                         
                    }  
                    interface 'e9d0cadd-34a1-4f2d-8be6-334fd4af0052' : FunctionalExchange 
                        connect source ::> 'Support '.'FOP 2'
                        to target ::> 'Transmit NLG Forces'.'Transmit NLG Structural Post'.'FIP 2' { 
                        @CapellaID { eid = "e9d0cadd-34a1-4f2d-8be6-334fd4af0052"; sid = "e9d0cadd-34a1-4f2d-8be6-334fd4af0052"; } 
                        attribute :>> isMulticast = false; 
                        attribute :>> isMultireceive = false; 
                        attribute :>> kindOfRate = RateKind::Unspecified; 
                        attribute :>> interfaceName = "Structural"; 
                         
                    }  
                    interface '1b0e1049-f651-458e-94c5-4381a74f18bb' : FunctionalExchange 
                        connect source ::> 'Provide Spring Support'.'FOP 1'
                        to target ::> 'Measure'.'Actuate NLG'.'Apply Force Runway'.'FIP 2' { 
                        @CapellaID { eid = "1b0e1049-f651-458e-94c5-4381a74f18bb"; } 
                        attribute :>> isMulticast = false; 
                        attribute :>> isMultireceive = false; 
                        attribute :>> kindOfRate = RateKind::Unspecified; 
                        attribute :>> interfaceName = "Deliver Spring Force"; 
                         
                    }  
                    interface 'a6323585-d7fe-48a4-9fd2-6c73636ff52d' : FunctionalExchange 
                        connect source ::> 'Measure'.'Actuate NLG'.'Control Pressure to Wheel'.'FOP 7'
                        to target ::> 'Release Selector Valve Pressure'.'FIP 1' { 
                        @CapellaID { eid = "a6323585-d7fe-48a4-9fd2-6c73636ff52d"; } 
                        attribute :>> isMulticast = false; 
                        attribute :>> isMultireceive = false; 
                        attribute :>> kindOfRate = RateKind::Unspecified; 
                        attribute :>> interfaceName = "Pressurized Hydraulic Center"; 
                         
                    }  
                    interface '3a359c3c-a4a2-411a-8961-29a1bfbea4c6' : FunctionalExchange 
                        connect source ::> 'Release Selector Valve Pressure'.'FOP 1'
                        to target ::> 'Store H Fluid'.'FIP 1' { 
                        @CapellaID { eid = "3a359c3c-a4a2-411a-8961-29a1bfbea4c6"; } 
                        attribute :>> isMulticast = false; 
                        attribute :>> isMultireceive = false; 
                        attribute :>> kindOfRate = RateKind::Unspecified; 
                        attribute :>> interfaceName = "Low Pressure Fluid"; 
                         
                    }  
                    interface 'c4b6b216-e81c-4e1b-b059-195564f4e397' : FunctionalExchange 
                        connect source ::> 'Release Door Valve Pressure '.'FOP 1'
                        to target ::> 'Store H Fluid'.'FIP 2' { 
                        @CapellaID { eid = "c4b6b216-e81c-4e1b-b059-195564f4e397"; } 
                        attribute :>> isMulticast = false; 
                        attribute :>> isMultireceive = false; 
                        attribute :>> kindOfRate = RateKind::Unspecified; 
                        attribute :>> interfaceName = "Low Pressure Fluid"; 
                         
                    }  
                    interface '58b22acb-b13f-4000-bdf5-222a6006c90c' : FunctionalExchange 
                        connect source ::> 'SupplyPressur'.'FOP 8'
                        to target ::> 'Control Pressure'.'FIP 1' { 
                        @CapellaID { eid = "58b22acb-b13f-4000-bdf5-222a6006c90c"; } 
                        attribute :>> isMulticast = false; 
                        attribute :>> isMultireceive = false; 
                        attribute :>> kindOfRate = RateKind::Unspecified; 
                        attribute :>> interfaceName = "No. 3 Hydraulic System"; 
                         
                    }  
                    interface 'dd24e1c6-d1aa-4685-ace8-724913363a1a' : FunctionalExchange 
                        connect source ::> 'Control Pressure'.'FOP 1'
                        to target ::> 'Release Door Valve Pressure '.'FIP 1' { 
                        @CapellaID { eid = "dd24e1c6-d1aa-4685-ace8-724913363a1a"; } 
                        attribute :>> isMulticast = false; 
                        attribute :>> isMultireceive = false; 
                        attribute :>> kindOfRate = RateKind::Unspecified; 
                        attribute :>> interfaceName = "Pressure"; 
                         
                    }  
                    interface '3fcc6e64-59a4-4362-8a29-7ef25d1d33ef' : FunctionalExchange 
                        connect source ::> 'Control Pressure'.'FOP 2'
                        to target ::> 'Move Door'.'FIP 1' { 
                        @CapellaID { eid = "3fcc6e64-59a4-4362-8a29-7ef25d1d33ef"; } 
                        attribute :>> isMulticast = false; 
                        attribute :>> isMultireceive = false; 
                        attribute :>> kindOfRate = RateKind::Unspecified; 
                        attribute :>> interfaceName = "Pressure"; 
                         
                    }  
                    interface '09f2e368-77ad-4836-b2f8-1a7c73051bec' : FunctionalExchange 
                        connect source ::> 'Move Door'.'FOP 1'
                        to target ::> 'Open and Close'.'FIP 1' { 
                        @CapellaID { eid = "09f2e368-77ad-4836-b2f8-1a7c73051bec"; } 
                        attribute :>> isMulticast = false; 
                        attribute :>> isMultireceive = false; 
                        attribute :>> kindOfRate = RateKind::Unspecified; 
                        attribute :>> interfaceName = "Open Closr"; 
                         
                    }  
                    interface '5dc9b5f4-d936-4948-bbdd-b5e7c20a6468' : FunctionalExchange 
                        connect source ::> 'Support '.'FOP 3'
                        to target ::> 'Open and Close'.'FIP 2' { 
                        @CapellaID { eid = "5dc9b5f4-d936-4948-bbdd-b5e7c20a6468"; } 
                        attribute :>> isMulticast = false; 
                        attribute :>> isMultireceive = false; 
                        attribute :>> kindOfRate = RateKind::Unspecified; 
                        attribute :>> interfaceName = "Support"; 
                         
                    }  
                    interface 'afaffcef-2120-4d31-a0f8-b21afbc81f2b' : FunctionalExchange 
                        connect source ::> 'Sense NLG State'.'FOP 7'
                        to target ::> 'Manage NLG Door'.'FIP 1' { 
                        @CapellaID { eid = "afaffcef-2120-4d31-a0f8-b21afbc81f2b"; } 
                        attribute :>> isMulticast = false; 
                        attribute :>> isMultireceive = false; 
                        attribute :>> kindOfRate = RateKind::Unspecified; 
                        attribute :>> interfaceName = "Door Position"; 
                         
                    }  
                    interface '5d56fd8d-edd8-4801-8e3f-c9aa26383600' : FunctionalExchange 
                        connect source ::> 'Manage NLG Door'.'FOP 1'
                        to target ::> 'Control Pressure'.'FIP 2' { 
                        @CapellaID { eid = "5d56fd8d-edd8-4801-8e3f-c9aa26383600"; } 
                        attribute :>> isMulticast = false; 
                        attribute :>> isMultireceive = false; 
                        attribute :>> kindOfRate = RateKind::Unspecified; 
                        attribute :>> interfaceName = "NLG Door"; 
                         
                    }  
                    interface '6e4c5e21-12e9-4feb-814e-b7c8aa43f8ea' : FunctionalExchange 
                        connect source ::> 'Store H Fluid'.'FOP 1'
                        to target ::> 'Supply Pressure'.'FIP 2' { 
                        @CapellaID { eid = "6e4c5e21-12e9-4feb-814e-b7c8aa43f8ea"; } 
                        attribute :>> isMulticast = false; 
                        attribute :>> isMultireceive = false; 
                        attribute :>> kindOfRate = RateKind::Unspecified; 
                        attribute :>> interfaceName = "H Fluid"; 
                         
                    }  
                    interface 'dbc3f5d5-2f48-4593-af18-e7139be3d59a' : FunctionalExchange 
                        connect source ::> 'Store H Fluid'.'FOP 2'
                        to target ::> 'Supply H3 Pressure'.'FIP 2' { 
                        @CapellaID { eid = "dbc3f5d5-2f48-4593-af18-e7139be3d59a"; } 
                        attribute :>> isMulticast = false; 
                        attribute :>> isMultireceive = false; 
                        attribute :>> kindOfRate = RateKind::Unspecified; 
                        attribute :>> interfaceName = "H Fluid"; 
                         
                    }  
                    interface '8a9a972f-7c53-4fde-8364-eca5e86c5fe5' : FunctionalExchange 
                        connect source ::> 'NLG Door Dump'.'FOP 1'
                        to target ::> 'Release Door Valve Pressure '.'FIP 2' { 
                        @CapellaID { eid = "8a9a972f-7c53-4fde-8364-eca5e86c5fe5"; } 
                        attribute :>> isMulticast = false; 
                        attribute :>> isMultireceive = false; 
                        attribute :>> kindOfRate = RateKind::Unspecified; 
                        attribute :>> interfaceName = "Door Dump "; 
                         
                    }  
                    interface 'ecfbd774-e962-4196-a4d1-d8026752c9e5' : FunctionalExchange 
                        connect source ::> 'NLG Dump'.'FOP 1'
                        to target ::> 'Release Selector Valve Pressure'.'FIP 2' { 
                        @CapellaID { eid = "ecfbd774-e962-4196-a4d1-d8026752c9e5"; } 
                        attribute :>> isMulticast = false; 
                        attribute :>> isMultireceive = false; 
                        attribute :>> kindOfRate = RateKind::Unspecified; 
                        attribute :>> interfaceName = "NLG Dump"; 
                         
                    }  
                    interface '01616769-4383-43bc-8c1d-2a6ead7c722f' : FunctionalExchange 
                        connect source ::> 'Control Gear'.'FOP 1'
                        to target ::> 'Provide Landing Gear Control'.'Provide'.'FIP 3' { 
                        @CapellaID { eid = "01616769-4383-43bc-8c1d-2a6ead7c722f"; } 
                        attribute :>> isMulticast = false; 
                        attribute :>> isMultireceive = false; 
                        attribute :>> kindOfRate = RateKind::Unspecified; 
                        attribute :>> interfaceName = "Gear Control"; 
                         
                    }  
                    interface '78c4630d-fda8-439f-abcf-3773df772c00' : FunctionalExchange 
                        connect source ::> 'NLG Gear Override'.'FOP 1'
                        to target ::> 'NLG Dump'.'FIP 1' { 
                        @CapellaID { eid = "78c4630d-fda8-439f-abcf-3773df772c00"; } 
                        attribute :>> isMulticast = false; 
                        attribute :>> isMultireceive = false; 
                        attribute :>> kindOfRate = RateKind::Unspecified; 
                        attribute :>> interfaceName = "Dump Overeide"; 
                         
                    }  
                    interface '49abf19d-43b3-49a7-a4c6-7cfe88216935' : FunctionalExchange 
                        connect source ::> 'NLG Door Overide'.'FOP 1'
                        to target ::> 'NLG Door Dump'.'FIP 1' { 
                        @CapellaID { eid = "49abf19d-43b3-49a7-a4c6-7cfe88216935"; } 
                        attribute :>> isMulticast = false; 
                        attribute :>> isMultireceive = false; 
                        attribute :>> kindOfRate = RateKind::Unspecified; 
                        attribute :>> interfaceName = "Door Overide"; 
                         
                    }  
                    ref :>> ownedFunctions =  ('Process Data',
                    'xmit / xceive',
                    'Action Report',
                    'Support Response',
                    'Persons Scanned',
                    'Provide Support',
                    'Interpreted Analysis Response',
                    'Initiate Mission',
                    'Analysis',
                    'Scan',
                    'Perform Detect',
                    'Site Support',
                    'Persons Supported',
                    'LOS Control',
                    'BLOS Control',
                    'Interpret Analysis',
                    'Extend Range',
                    'Monitor Execution',
                    'Update SITREP',
                    'Interpret SITREP',
                    'Ad Hoc Mission Update',
                    'Provide C&amp;C SITREP',
                    'Ad Hoc Mission Update Response',
                    'Ad Hoc Mission Execution Update',
                    'Capture Photos',
                    'Collect Information  Distressed Location ',
                    'Locate Trapped People',
                    'Capture Video',
                    'Natural Disaster ',
                    'Define Overflight Recon Mission',
                    'Relay Overflight Data from Drone Mission',
                    'Perform Overflight Recon Mission',
                    'Relay to Operator',
                    'Gather 35',
                    'Operator Mission Planning',
                    'Receive Mission Order',
                    'Activate Scan',
                    'Image Storage',
                    'PhysicalFunction 39',
                    'PhysicalFunction 40',
                    'PhysicalFunction 41',
                    'Supply H3 Pressure',
                    'Measure',
                    'Provide Landing Gear Control',
                    'Provide Landing Gear Indication',
                    'Sense Pressure',
                    'Provide',
                    'Support ',
                    'Transmit LG Force',
                    'Provide Status',
                    'Provide Ground  Force',
                    'Provide Friction',
                    'Sense NLG State',
                    'Sense Hardware',
                    'Tranmit',
                    'Transmit Ground Force',
                    'Transmit NLG Forces',
                    'Support LG',
                    'Supply Pressure',
                    'SupplyPressur',
                    'Duplicate 67',
                    'ActuateLMLG',
                    'Actuate RMLG',
                    'Channel',
                    'Maintain Pressure',
                    'Store',
                    'Pump Fluid',
                    'Control',
                    'Pump Fliud',
                    'Regulate',
                    'Isolate ',
                    'Slow Rotation',
                    'Sense Weight on Wheels',
                    'Sense Weight on Wheels 2',
                    'Provide Spring Support',
                    'Manage NLG',
                    'Store H Fluid',
                    'Release Selector Valve Pressure',
                    'Release Door Valve Pressure ',
                    'Control Pressure',
                    'Move Door',
                    'Open and Close',
                    'Manage NLG Door',
                    'NLG Dump',
                    'NLG Door Dump',
                    'Control Gear',
                    'NLG Gear Override',
                    'NLG Door Overide'); 
                     
                    ref :>> ownedFunctionalExchanges =  ('0dec75ca-92e1-492c-b25d-fa132c5454c2',
                    '93290df8-fed9-49d1-beed-b9aaf7a44f24',
                    'a9c8c5d1-a0aa-4fa8-9841-84cf667fb6e7',
                    'efc215a0-6f00-45af-903a-ca7251958835',
                    'e8af4590-715f-466e-ad38-6e47c27d2951',
                    'f234bce6-52e7-49e9-bd9d-eeb5075a68b2',
                    '4e29bbc1-ea33-40a6-a5a2-61e1dbf63ae6',
                    '4dd97418-d007-46d9-8f7c-87f3502c3ec5',
                    'f072ef8d-3125-471c-829f-6f95ca80097e',
                    'ad3df3f1-f31f-4b45-9438-4f06a86e4152',
                    '98a1d99f-7d1b-4bf7-8389-e9648c7ba5c0',
                    '4eb9f09b-b4e7-49a1-a73a-3346c16bd1f9',
                    '8aa7cbd4-27d0-4264-8599-c0c6acae31de',
                    'd1a97504-b78b-41b9-acd8-4a02fb1a33c0',
                    '42a21bb7-1b94-4ba2-86ea-e141e9b4c939',
                    'eef67666-861e-4bce-8358-80dc9d14d21b',
                    '9b5b76ce-98bf-45e6-9cfd-385ca0ce3e9d',
                    '85a221ae-9eef-48ae-b69b-7979faced74a',
                    '92c595ae-1023-4c82-8220-7f2b2eb1bdd0',
                    'a16b1418-33f2-4af9-b77b-52af39f442f4',
                    '84a01918-f6c0-4f3b-9697-4a42fd16534e',
                    '795262b4-e5cc-4f7e-b06e-7108bfe01fd4',
                    'ab243386-52d7-459d-9707-6a18abbb9b83',
                    '141959c3-cb9c-4778-88fa-dcf48fc230b3',
                    'ff75426f-12a6-4208-8130-70b4c5c0c3f6',
                    '1dc07bf7-2f2a-408a-b55d-537a90f10368',
                    '3f900ac2-d70a-4712-b1f3-2579db25b4e8',
                    'a60fd365-b419-40ea-b7ba-12a94748c12e',
                    '844fdd8e-cc79-44c9-abe8-9d977e6bf76d',
                    '12340e91-350b-40c8-8074-7d3584ea3bea',
                    'dab62d0a-f03a-4dc7-b11d-189881291644',
                    '1e89b679-4ee5-4fd3-8e47-a955e14e88a1',
                    '71ada17d-39af-44a8-ab4d-4a1e92c6231e',
                    'b141216c-80c6-4f2e-b648-67772db4f2b3',
                    '85621e3d-1a84-45af-9235-c37b1a7aa9bd',
                    '619f3dfd-edc3-4a6a-95f2-27ff70ec6afe',
                    '7de4d9d6-677f-49c9-8f58-fff49f71b043',
                    'ff1adf05-fc1b-49b2-b2c8-df6a14d56eaf',
                    'bddbcd0d-3df2-4bff-95b1-9b19a6cdb267',
                    '15984110-47d2-40e5-adc6-049128b8eb66',
                    '30c4fd48-fd98-416e-9086-feb98586279d',
                    '4d82d33b-ac98-4319-bf5e-f8e2cab8e33d',
                    '24a38b00-19b1-48de-850e-4f435028df88',
                    '3636a890-f283-4557-8fbf-87c7fbd83013',
                    '9a7c1e82-e3d2-4539-a01b-7569bbb0939f',
                    '96917dd7-0d19-4829-8049-ed4bfa50c570',
                    'c9066143-21d9-48af-b056-4d1608b81bed',
                    '6224d738-93ed-415c-967f-5e125cf75016',
                    '41b60723-f7c9-414c-9e34-2b50804b839b',
                    'af1f32da-c8de-4166-8d67-a8a392ae3cca',
                    '7face944-9535-447d-a41b-045e590a65dd',
                    '476a9f9a-b908-470d-8d8b-0b443489cb84',
                    '5620edc6-3057-4812-906f-d26b02ad52dd',
                    '6f08837b-eae6-40ce-b08c-aca538a78912',
                    'adb0d0e1-fdb9-48dd-9e01-1c9444a10c8e',
                    '7fbdfbe1-b89b-4fbb-88f9-bc65dfbc1379',
                    'f387bf1c-81b3-444b-903f-9b1aa25c00f1',
                    '5441eb90-cfa9-4f55-96de-54e7625462c1',
                    '73b4b16a-bf09-4603-81c1-9748d4dae983',
                    '3dd2c494-03e4-4511-8229-90df30f2fb6a',
                    'e586d180-2195-4911-ae8a-04dcef046776',
                    'e464a43f-96dd-4638-84e3-50dcae0fc54c',
                    '2dc4a6c7-e5da-4c4b-b985-c50c84750e56',
                    '0fe580e4-7e35-48b1-898c-3d7c1f790ec8',
                    '800ff49e-cc73-4b71-9e22-27283841597f',
                    '59428dfe-81b6-4d97-8654-c1d4bfb73819',
                    '16a8d621-e576-4365-bbb3-e65bea6bff08',
                    '2ac5535d-5a1f-448f-9a24-cdb778d6e8db',
                    '51e005b5-44cd-4c32-a336-21bb4f8f1408',
                    'e8026413-6760-47f1-bdb5-eff8b873c988',
                    '08a41a71-a931-4311-9987-7d9fe0971867',
                    'e51a349f-3ff9-42b6-901f-f07199aa65c3',
                    'a9bde180-4f8d-42a5-b923-4e4752822080',
                    '4c3fd424-a65e-46d2-8687-718dfacf40e2',
                    '95abeb94-ee12-44d8-96f4-de9c3e32badf',
                    '89842b61-fafa-4233-803f-5059b8ac41da',
                    'cc844e5e-66ad-40b1-b1de-388d7aaafd88',
                    'dee65853-313f-4ca0-974d-7c0587c78f7d',
                    'e1a8badb-13d4-4949-b989-39677c7349da',
                    'b9cdc645-a99b-4cb1-a8c8-5111fdd8db62',
                    '374b5c8a-4916-4a0d-a034-b81b7ac79b2a',
                    'ae78d464-1d1a-4c52-85da-8e596ee0dd6b',
                    '9fc76035-36cb-46e9-af40-9f319ce9dd9b',
                    '76d4943d-d74b-4546-84d1-4e6ac62e216e',
                    'd3106823-a315-407a-9dbc-d9d2512ba147',
                    '77535c9e-26f9-48f9-a652-dccbb875f365',
                    '678f50d6-4c8e-4ae7-8486-c5cae7f377e4',
                    '40cd96ef-accd-416b-8716-89d7c25477f3',
                    'c1721ee8-7264-4c86-887b-39c3bbad311c',
                    '7cee4409-2d70-49cf-9ffa-b6541a64d7e4',
                    'cd3e88dc-1a45-4457-bb04-6d0229ca538f',
                    '14d27697-47bf-4616-9758-b1dd5dcf8edf',
                    '34a60779-44ba-4915-af24-5fd1877d6cad',
                    '1d0ef78d-bb0c-4929-ace7-8d0818fef271',
                    '004b4ee4-f50b-47d8-8ab8-684a3165d440',
                    '832de532-5107-4edb-a0e5-b610d918034f',
                    'e3479523-c52a-4d52-a6fd-5c74b60d7431',
                    'e9d0cadd-34a1-4f2d-8be6-334fd4af0052',
                    '1b0e1049-f651-458e-94c5-4381a74f18bb',
                    'a6323585-d7fe-48a4-9fd2-6c73636ff52d',
                    '3a359c3c-a4a2-411a-8961-29a1bfbea4c6',
                    'c4b6b216-e81c-4e1b-b059-195564f4e397',
                    '58b22acb-b13f-4000-bdf5-222a6006c90c',
                    'dd24e1c6-d1aa-4685-ace8-724913363a1a',
                    '3fcc6e64-59a4-4362-8a29-7ef25d1d33ef',
                    '09f2e368-77ad-4836-b2f8-1a7c73051bec',
                    '5dc9b5f4-d936-4948-bbdd-b5e7c20a6468',
                    'afaffcef-2120-4d31-a0f8-b21afbc81f2b',
                    '5d56fd8d-edd8-4801-8e3f-c9aa26383600',
                    '6e4c5e21-12e9-4feb-814e-b7c8aa43f8ea',
                    'dbc3f5d5-2f48-4593-af18-e7139be3d59a',
                    '8a9a972f-7c53-4fde-8364-eca5e86c5fe5',
                    'ecfbd774-e962-4196-a4d1-d8026752c9e5',
                    '01616769-4383-43bc-8c1d-2a6ead7c722f',
                    '78c4630d-fda8-439f-abcf-3773df772c00',
                    '49abf19d-43b3-49a7-a4c6-7cfe88216935'); 
                     
                }  
            } 
            package 'Capabilities' {
                @PackageMeta {
                    type = "CapabilityRealizationPkg";
                } 
                @CapellaID { eid = "12a4140c-6d5a-47ba-8670-9eec22852468"; } 
            } 
        } 
    } 
}
